Attribute VB_Name = "CommonDigitalString"
Option Explicit

Public Function isNum(str As String) As Boolean

    Dim i As Integer
    Dim flag As Boolean
    flag = False
    isNum = True
    For i = 1 To Len(str)
        If isDigit(Mid(str, i, 1)) = False Then
            isNum = False
        End If
    Next

End Function

Public Function isDigit(str As String) As Boolean

    Dim arr(0 To 9) As String
    Dim i As Integer
    arr(0) = "0"
    arr(1) = "1"
    arr(2) = "2"
    arr(3) = "3"
    arr(4) = "4"
    arr(5) = "5"
    arr(6) = "6"
    arr(7) = "7"
    arr(8) = "8"
    arr(9) = "9"
    isDigit = False
    For i = 0 To 9
        If str = arr(i) Then
            isDigit = True
        End If
    Next

End Function

Attribute VB_Name = "ParamReplica"
Option Explicit

Public Sub extractParameters(prtDoc As PartDocument, ByRef primitiveType As String, foundParams As Collection)

    ' Get the primitive type from the udf name from PartBody of the daughter volume
    Dim i As Integer
    Dim udfName As String
    udfName = prtDoc.Part.MainBody.Shapes.Item(1).Name
    For i = 1 To formReplica.listOfPrimitives.Count
        If InStr(1, udfName, formReplica.listOfPrimitives.Item(i), vbTextCompare) Then
            primitiveType = formReplica.listOfPrimitives.Item(i)
            Exit For
        End If
    Next i

    ' Specify names of parameters to search depending on the primitive type
    Dim paramNamesToSearch As New Collection
    Select Case primitiveType
    Case "G4Box":
        paramNamesToSearch.Add "pX", "pX"
        paramNamesToSearch.Add "pY", "pY"
        paramNamesToSearch.Add "pZ", "pZ"
    Case "G4Cons":
        paramNamesToSearch.Add "pSPhi", "pSPhi"
        paramNamesToSearch.Add "pDPhi", "pDPhi"
        paramNamesToSearch.Add "pDz", "pDz"
        paramNamesToSearch.Add "pRmin1", "pRmin1"
        paramNamesToSearch.Add "pRmax1", "pRmax1"
        paramNamesToSearch.Add "pRmin2", "pRmin2"
        paramNamesToSearch.Add "pRmax2", "pRmax2"
    Case "G4Tubs":
        paramNamesToSearch.Add "pDz", "pDz"
        paramNamesToSearch.Add "pSPhi", "pSPhi"
        paramNamesToSearch.Add "pDPhi", "pDPhi"
        paramNamesToSearch.Add "pRMin", "pRMin"
        paramNamesToSearch.Add "pRMax", "pRMax"
    Case "G4Sphere":
        paramNamesToSearch.Add "pSPhi", "pSPhi"
        paramNamesToSearch.Add "pDPhi", "pDPhi"
        paramNamesToSearch.Add "pSTheta", "pSTheta"
        paramNamesToSearch.Add "pDTheta", "pDTheta"
        paramNamesToSearch.Add "pRmin", "pRmin"
        paramNamesToSearch.Add "pRmax", "pRmax"
    Case Else:
        ' ERROR
        formReplica.lblStatus.Caption = "The primitive could not be recognized."
        formReplica.txtPrimType.Text = ""
        formReplica.txtAxis.Text = ""
        formReplica.txtCompNum.Text = ""
        formReplica.txtCompWidth.Text = ""
        Exit Sub
    End Select

    ' Search for parameters
    Dim j As Integer
    Dim params As Parameters
    Set params = prtDoc.Part.Parameters
    For i = 1 To params.Count
        For j = 1 To paramNamesToSearch.Count
            If InStr(1, params.Item(i).Name, udfName + "\" + paramNamesToSearch.Item(j), vbTextCompare) Then
                foundParams.Add params.Item(i), paramNamesToSearch.Item(j)
            End If
        Next j
    Next i

End Sub

Public Sub compute()

    ' GUI
    formReplica.lblStatus.Caption = "Please, wait. Trying to get the parameters of the pattern."

    ' Extract the parameters of the daughter volume
    Dim daughterPrtDoc As PartDocument
    Set daughterPrtDoc = formReplica.PartVolumePair.Item(formReplica.PhysicalPartComboBox.Text)
    Dim daughterType As String
    Dim daughterFoundParams As New Collection
    Call extractParameters(daughterPrtDoc, daughterType, daughterFoundParams)

    ' Extract the parameters of the mother volume
    Dim motherPrtDoc As PartDocument
    Set motherPrtDoc = formReplica.PartVolumePair.Item(formReplica.LogicalPartComboBox.Text)
    Dim motherType As String
    Dim motherFoundParams As New Collection
    Call extractParameters(motherPrtDoc, motherType, motherFoundParams)

    ' Recognize the axis of replication
    ' Here also check that the parameters' value correspond to replica
    If daughterType <> motherType Then
        ' ERROR
        formReplica.lblStatus.Caption = "The primitive type of the daughter volume is not same as of the mother volume."
        formReplica.txtPrimType.Text = ""
        formReplica.txtAxis.Text = ""
        formReplica.txtCompNum.Text = ""
        formReplica.txtCompWidth.Text = ""
        Exit Sub
    End If

    Dim factor1 As Double
    Dim factor2 As Double
    Dim factor3 As Double
    Dim axis As String
    Select Case daughterType
    Case "G4Box":
        factor1 = Val(CommaToDot(motherFoundParams.Item("pX").ValueAsString)) / Val(CommaToDot(daughterFoundParams.Item("pX").ValueAsString))
        factor2 = Val(CommaToDot(motherFoundParams.Item("pY").ValueAsString)) / Val(CommaToDot(daughterFoundParams.Item("pY").ValueAsString))
        factor3 = Val(CommaToDot(motherFoundParams.Item("pZ").ValueAsString)) / Val(CommaToDot(daughterFoundParams.Item("pZ").ValueAsString))
        If (factor1 > 1 And factor2 = 1 And factor3 = 1) Then
            axis = "X"
            formReplica.txtCompNum.Text = Trim(str(factor1))
            formReplica.txtCompWidth.Text = str(Val(CommaToDot(daughterFoundParams.Item("pX").ValueAsString)) * 2#) + " mm" ' ???
        ElseIf (factor1 = 1 And factor2 > 1 And factor3 = 1) Then
            axis = "Y"
            formReplica.txtCompNum.Text = Trim(str(factor2))
            formReplica.txtCompWidth.Text = str(Val(CommaToDot(daughterFoundParams.Item("pY").ValueAsString)) * 2#) + " mm" ' ???
        ElseIf (factor1 = 1 And factor2 = 1 And factor3 > 1) Then
            axis = "Z"
            formReplica.txtCompNum.Text = Trim(str(factor3))
            formReplica.txtCompWidth.Text = str(Val(CommaToDot(daughterFoundParams.Item("pZ").ValueAsString)) * 2#) + " mm" ' ???
        Else
            ' ERROR
            formReplica.lblStatus.Caption = "The axis of replication could not have been computed."
            formReplica.txtPrimType.Text = ""
            formReplica.txtAxis.Text = ""
            formReplica.txtCompNum.Text = ""
            formReplica.txtCompWidth.Text = ""
            Exit Sub
        End If

    Case "G4Cons":
        If motherFoundParams.Item("pRmin1").ValueAsString = daughterFoundParams.Item("pRmin1").ValueAsString And _
           motherFoundParams.Item("pRmax1").ValueAsString = daughterFoundParams.Item("pRmax1").ValueAsString And _
           motherFoundParams.Item("pRmin2").ValueAsString = daughterFoundParams.Item("pRmin2").ValueAsString And _
           motherFoundParams.Item("pRmax2").ValueAsString = daughterFoundParams.Item("pRmax2").ValueAsString And _
           motherFoundParams.Item("pDz").ValueAsString = daughterFoundParams.Item("pDz").ValueAsString Then
            factor1 = Val(CommaToDot(motherFoundParams.Item("pDPhi").ValueAsString)) / Val(CommaToDot(daughterFoundParams.Item("pDPhi").ValueAsString))
            If (factor1 > 1) Then
                axis = "P"
                formReplica.txtCompNum.Text = Trim(str(factor1))
                formReplica.txtCompWidth.Text = Val(CommaToDot(daughterFoundParams.Item("pDPhi").ValueAsString))
            End If
        Else
            ' ERROR
            formReplica.lblStatus.Caption = "The axis of replication could not have been computed."
            formReplica.txtPrimType.Text = ""
            formReplica.txtAxis.Text = ""
            formReplica.txtCompNum.Text = ""
            formReplica.txtCompWidth.Text = ""
            Exit Sub
        End If

    Case "G4Tubs":
        If motherFoundParams.Item("pRMin").ValueAsString = daughterFoundParams.Item("pRMin").ValueAsString And _
           motherFoundParams.Item("pRMax").ValueAsString = daughterFoundParams.Item("pRMax").ValueAsString Then
            factor1 = Val(CommaToDot(motherFoundParams.Item("pDz").ValueAsString)) / Val(CommaToDot(daughterFoundParams.Item("pDz").ValueAsString))
            factor2 = Val(CommaToDot(motherFoundParams.Item("pDPhi").ValueAsString)) / Val(CommaToDot(daughterFoundParams.Item("pDPhi").ValueAsString))
            If (factor1 > 1 And factor2 = 1) Then
                axis = "Z"
                formReplica.txtCompNum.Text = Trim(str(factor1))
                formReplica.txtCompWidth.Text = Val(CommaToDot(daughterFoundParams.Item("pDz").ValueAsString))
            ElseIf (factor1 = 1 And factor2 > 1) Then
                axis = "P"
                formReplica.txtCompNum.Text = Trim(str(factor2))
                formReplica.txtCompWidth.Text = Val(CommaToDot(daughterFoundParams.Item("pDPhi").ValueAsString))
            End If
        Else
            ' ERROR
            formReplica.lblStatus.Caption = "The axis of replication could not have been computed."
            formReplica.txtPrimType.Text = ""
            formReplica.txtAxis.Text = ""
            formReplica.txtCompNum.Text = ""
            formReplica.txtCompWidth.Text = ""
            Exit Sub
        End If

    Case "G4Sphere":
        If motherFoundParams.Item("pRmin").ValueAsString = daughterFoundParams.Item("pRmin").ValueAsString And _
           motherFoundParams.Item("pRmax").ValueAsString = daughterFoundParams.Item("pRmax").ValueAsString And _
           motherFoundParams.Item("pSTheta").ValueAsString = daughterFoundParams.Item("pSTheta").ValueAsString And _
           motherFoundParams.Item("pDTheta").ValueAsString = daughterFoundParams.Item("pDTheta").ValueAsString Then
            factor1 = Val(CommaToDot(motherFoundParams.Item("pDPhi").ValueAsString)) / Val(CommaToDot(daughterFoundParams.Item("pDPhi").ValueAsString))
            If (factor1 > 1) Then
                axis = "P"
                formReplica.txtCompNum.Text = Trim(str(factor1))
                formReplica.txtCompWidth.Text = Val(CommaToDot(daughterFoundParams.Item("pDPhi").ValueAsString))
            End If
        Else
            ' ERROR
            formReplica.lblStatus.Caption = "The axis of replication could not have been computed."
            formReplica.txtPrimType.Text = ""
            formReplica.txtAxis.Text = ""
            formReplica.txtCompNum.Text = ""
            formReplica.txtCompWidth.Text = ""
            Exit Sub
        End If

    End Select

    formReplica.txtPrimType.Text = daughterType
    formReplica.txtAxis.Text = axis + " axis"

    ' GUI
    formReplica.lblStatus.Caption = "Computed."

End Sub

Attribute VB_Name = "Replica"
Sub CATMain()
    
    formReplica.Show

End Sub

Attribute VB_Name = "Support"
Option Explicit

Const STEPADD = 0.002
Const CIRCSHIFT = 0.02

Public Sub coincidence_std_planes()

    Dim ProductDoc As ProductDocument
    Set ProductDoc = CATIA.ActiveDocument
    
    Dim Product1 As Product
    Dim Product2 As Product
    
    Dim reference1 As Reference
    Dim reference2 As Reference
    
    Dim str1 As String
    Dim str2 As String
    Dim str3 As String
    Dim str4 As String
    Dim flag As Boolean
    
    Dim ConstraintsCollection As Constraints
    Set ConstraintsCollection = ProductDoc.Product.Connections("CATIAConstraints")
    
    Dim myConstraint As Constraint
    Dim i As Integer
    
    For i = 1 To ProductDoc.Product.Products.Count
        If (ProductDoc.Product.Products.Item(i).PartNumber = formReplica.PhysicalPartComboBox.Text) Then
            Set Product1 = ProductDoc.Product.Products.Item(i)
        End If
        If (ProductDoc.Product.Products.Item(i).PartNumber = formReplica.LogicalPartComboBox.Text) Then
            Set Product2 = ProductDoc.Product.Products.Item(i)
        End If
    Next i
    
    'xy planes processing
    flag = False
    str1 = ProductDoc.Product.Name + "/" + Product1.Name + "/!xy plane"
    str2 = ProductDoc.Product.Name + "/" + Product2.Name + "/!xy plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If
    
    'yz planes processing
    flag = False
    str1 = ProductDoc.Product.Name + "/" + Product1.Name + "/!yz plane"
    str2 = ProductDoc.Product.Name + "/" + Product2.Name + "/!yz plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If
    
    'zx planes processing
    flag = False
    str1 = ProductDoc.Product.Name + "/" + Product1.Name + "/!zx plane"
    str2 = ProductDoc.Product.Name + "/" + Product2.Name + "/!zx plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If

End Sub

Public Sub generateTransformations(partDoc As PartDocument)

    Dim hybShpFactory As HybridShapeFactory
    Dim shpFactory As ShapeFactory
    Dim origin As OriginElements
    Dim refPlaneXY As Reference
    Dim refPlaneYZ As Reference
    Dim refPlaneZX As Reference
    Dim sel As Selection
    Dim visPropSet As VisPropertySet

    Set hybShpFactory = partDoc.Part.HybridShapeFactory
    Set shpFactory = partDoc.Part.ShapeFactory
    Set origin = partDoc.Part.OriginElements
    Set refPlaneXY = partDoc.Part.CreateReferenceFromObject(origin.PlaneXY)
    Set refPlaneYZ = partDoc.Part.CreateReferenceFromObject(origin.PlaneYZ)
    Set refPlaneZX = partDoc.Part.CreateReferenceFromObject(origin.PlaneZX)
    Set sel = CATIA.ActiveDocument.Selection
    Set visPropSet = sel.VisProperties

    Dim Intersection_XY_ZX As HybridShapeIntersection
    Dim Intersection_YZ_XY As HybridShapeIntersection
    Dim Intersection_ZX_YZ As HybridShapeIntersection

    'Z axis preparation
    Set Intersection_ZX_YZ = hybShpFactory.AddNewIntersection(refPlaneZX, refPlaneYZ)
    Intersection_ZX_YZ.PointType = 0
    partDoc.Part.Bodies.Item(partDoc.Part.Bodies.Count).InsertHybridShape Intersection_ZX_YZ
'    partDoc.Part.InWorkObject = Intersection_ZX_YZ
    Intersection_ZX_YZ.Name = "Z axis"
    sel.Clear
    sel.Add Intersection_ZX_YZ
    visPropSet.SetShow catVisPropertyNoShowAttr
    sel.Clear
'    partDoc.Part.Update
    'Y axis preparation
    Set Intersection_YZ_XY = hybShpFactory.AddNewIntersection(refPlaneYZ, refPlaneXY)
    Intersection_YZ_XY.PointType = 0
    partDoc.Part.Bodies.Item(partDoc.Part.Bodies.Count).InsertHybridShape Intersection_YZ_XY
'    partDoc.Part.InWorkObject = Intersection_YZ_XY
    Intersection_YZ_XY.Name = "Y axis"
    sel.Clear
    sel.Add Intersection_YZ_XY
    visPropSet.SetShow catVisPropertyNoShowAttr
    sel.Clear
'    partDoc.Part.Update
    'X axis preparation
    Set Intersection_XY_ZX = hybShpFactory.AddNewIntersection(refPlaneXY, refPlaneZX)
    Intersection_XY_ZX.PointType = 0
    partDoc.Part.Bodies.Item(partDoc.Part.Bodies.Count).InsertHybridShape Intersection_XY_ZX
'    partDoc.Part.InWorkObject = Intersection_XY_ZX
    Intersection_XY_ZX.Name = "X axis"
    sel.Clear
    sel.Add Intersection_XY_ZX
    visPropSet.SetShow catVisPropertyNoShowAttr
    sel.Clear
'    partDoc.Part.Update

    Dim refAxisX As Reference
    Dim refAxisY As Reference
    Dim refAxisZ As Reference
    Dim hybShpRotX As HybridShapeRotate
    Dim hybShpRotY As HybridShapeRotate
    Dim hybShpRotZ As HybridShapeRotate
    Dim hybShpTrans As HybridShapeTranslate
    Dim rotX As Rotate
    Dim rotY As Rotate
    Dim rotZ As Rotate
    Dim trans As Translate

    'Rotate by Z axis creation
    Set refAxisZ = partDoc.Part.CreateReferenceFromObject(Intersection_ZX_YZ)
    Set rotZ = shpFactory.AddNewRotate2(refAxisZ, 0)
    Set hybShpRotZ = rotZ.HybridShape
    hybShpRotZ.RotationType = 0
    hybShpRotZ.axis = refAxisZ
    hybShpRotZ.Name = "Rotate.Z"
'    partDoc.Part.InWorkObject = hybShpRotZ
'    partDoc.Part.Update
    'Rotate by Y axis creation
    Set refAxisY = partDoc.Part.CreateReferenceFromObject(Intersection_YZ_XY)
    Set rotY = shpFactory.AddNewRotate2(refAxisY, 0)
    Set hybShpRotY = rotY.HybridShape
    hybShpRotY.RotationType = 0
    hybShpRotY.axis = refAxisY
    hybShpRotY.Name = "Rotate.Y"
'    partDoc.Part.InWorkObject = hybShpRotY
'    partDoc.Part.Update
    'Rotate by X axis creation
    Set refAxisX = partDoc.Part.CreateReferenceFromObject(Intersection_XY_ZX)
    Set rotX = shpFactory.AddNewRotate2(refAxisX, 0)
    Set hybShpRotX = rotX.HybridShape
    hybShpRotX.RotationType = 0
    hybShpRotX.axis = refAxisX
    hybShpRotX.Name = "Rotate.X"
'    partDoc.Part.InWorkObject = hybShpRotX
'    partDoc.Part.Update

    'Translation
    Set trans = shpFactory.AddNewTranslate2(0)
    Set hybShpTrans = trans.HybridShape
    hybShpTrans.VectorType = 2

    'Для G4Sphere и G4Tubs понадобилось достать параметр pPhi материнского и дочернего объема
    Dim prodDoc As ProductDocument
    Set prodDoc = CATIA.ActiveDocument
    Dim childPartParams As Parameters
    Dim partParams As Parameters
    Set partParams = partDoc.Part.Parameters
    Dim motherShapeName  As String
    Dim childShapeName As String
    Dim motherSPhiVal As Double
    Dim childSPhiVal As Double
    Dim childPartName As String
    
    If ((formReplica.txtPrimType.Text = "G4Sphere" Or formReplica.txtPrimType.Text = "G4Tubs") And formReplica.txtAxis.Text = "Phi axis") Then ' or "P axis" ???
        motherShapeName = partDoc.Part.Bodies.Item("PartBody").Shapes.Item(1).Name
        motherSPhiVal = Val(Replace(partParams.Item(partDoc.Part.Name + "\PartBody\" + motherShapeName + "\pSPhi").ValueAsString, ",", "."))
        childPartName = partDoc.Part.Bodies.Item(partDoc.Part.Bodies.Count).Shapes.Item(1).SourceProduct.PartNumber 'solid последего body
        Dim childPartDoc As PartDocument
        Set childPartDoc = formReplica.PartVolumePair.Item(childPartName)
        childShapeName = childPartDoc.Part.Bodies.Item("PartBody").Shapes.Item(1).Name
        Set childPartParams = childPartDoc.Part.Parameters
        childSPhiVal = Val(Replace(childPartParams.Item(childPartDoc.Part.Name + "\PartBody\" + childShapeName + "\pSPhi").ValueAsString, ",", "."))
    End If

    hybShpTrans.CoordXValue = 0
    hybShpTrans.CoordYValue = 0
    hybShpTrans.CoordZValue = 0
    Select Case formReplica.txtAxis.Text
    Case "X axis"
        hybShpTrans.CoordXValue = (Val(formReplica.txtCompNum.Text) - 1) * 0.5 * Val(formReplica.txtCompWidth.Text) / 1000#
    Case "Y axis"
        hybShpTrans.CoordYValue = (Val(formReplica.txtCompNum.Text) - 1) * 0.5 * Val(formReplica.txtCompWidth.Text) / 1000#
    Case "Z axis"
        hybShpTrans.CoordZValue = (Val(formReplica.txtCompNum.Text) - 1) * 0.5 * Val(formReplica.txtCompWidth.Text) / 1000#
    Case "Phi axis"
        rotZ.Angle.Value = motherSPhiVal - childSPhiVal
    End Select

'    partDoc.part.InWorkObject = hybShpTrans
'    partDoc.part.Update
    
End Sub

Public Sub generatePattern(partDoc As PartDocument)

    Dim prt As Part
    Dim shpFactory As ShapeFactory
    Dim objToPat As Shape
    Dim bd As Body
    Set prt = partDoc.Part
    Set shpFactory = prt.ShapeFactory
    Set objToPat = prt.Bodies.Item(prt.Bodies.Count).Shapes.Item(prt.Bodies.Item(prt.Bodies.Count).Shapes.Count)
    Set bd = prt.Bodies.Item(prt.Bodies.Count)

    Dim Intersection_XY_ZX As HybridShapeIntersection
    Dim Intersection_YZ_XY As HybridShapeIntersection
    Dim Intersection_ZX_YZ As HybridShapeIntersection
    Set Intersection_XY_ZX = bd.HybridShapes.GetItem("X axis")
    Set Intersection_YZ_XY = bd.HybridShapes.GetItem("Y axis")
    Set Intersection_ZX_YZ = bd.HybridShapes.GetItem("Z axis")

    Dim prefix As String
    prefix = "Replica."

    Dim crPat As RectPattern
    Dim crCirc As CircPattern

    Select Case formReplica.txtAxis.Text
        Case "X axis"
            Set crPat = shpFactory.AddNewRectPattern(objToPat, Val(formReplica.txtCompNum.Text), 1, Val(formReplica.txtCompWidth.Text) + STEPADD, 10#, _
                                                                1, 1, Intersection_XY_ZX, Intersection_YZ_XY, False, False, 0#)
            crPat.Name = prefix & "X"
        Case "Y axis"
            Set crPat = shpFactory.AddNewRectPattern(objToPat, Val(formReplica.txtCompNum.Text), 1, Val(formReplica.txtCompWidth.Text) + STEPADD, 10#, _
                                                                1, 1, Intersection_YZ_XY, Intersection_ZX_YZ, False, False, 0#)
            crPat.Name = prefix & "Y"
        Case "Z axis"
            Set crPat = shpFactory.AddNewRectPattern(objToPat, Val(formReplica.txtCompNum.Text), 1, Val(formReplica.txtCompWidth.Text) + STEPADD, 10#, _
                                                                1, 1, Intersection_ZX_YZ, Intersection_XY_ZX, False, False, 0#)
            crPat.Name = prefix & "Z"
        Case "P axis"
            Dim pattStep As Double
            pattStep = Val(formReplica.txtCompWidth.Text) + CIRCSHIFT
            Set crCirc = shpFactory.AddNewCircPattern(objToPat, 1, Val(formReplica.txtCompNum.Text), 1#, pattStep, _
                                                                1, 1, Intersection_ZX_YZ, Intersection_ZX_YZ, True, 0#, True)
            crCirc.Name = prefix & "P"
            crCirc.AngularRepartition.AngularSpacing.Value = pattStep
    End Select

    ' Update
'    partDoc.Part.Update

End Sub

Public Function CommaToDot(inputString As String) As String
    
    CommaToDot = Replace(inputString, ",", ".")

End Function

Attribute VB_Name = "formReplica"
Attribute VB_Base = "0{1213AE32-3026-4384-8D59-FDEF21E7CCD3}{2F0DD17D-47FB-42F0-BEDF-7C8862E05530}"
Attribute VB_GlobalNameSpace = False
Attribute VB_Creatable = False
Attribute VB_PredeclaredId = True
Attribute VB_Exposed = False
Attribute VB_TemplateDerived = False
Attribute VB_Customizable = False
Option Explicit

Public listOfPrimitives As Collection

Public PartVolumePair As Collection
' Key - part number ("G4_World"), item - pointer to the document ("G4_World.CATPart")

Private Sub LogicalPartComboBox_Change()
    If (PhysicalPartComboBox.Text <> "") And (LogicalPartComboBox.Text <> "") Then
        Call nameGenerate
        Call compute
    End If
End Sub

Private Sub PhysicalPartComboBox_Change()
    If (PhysicalPartComboBox.Text <> "") And (LogicalPartComboBox.Text <> "") Then
        Call nameGenerate
        Call compute
    End If
End Sub

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument
    
    ' Translate to design mode
'    MsgBox "Parts in this product are to be translated into 'Design Mode'" + vbNewLine + "This may take a few minutes, please wait.", vbExclamation, "Translate to Design mode"
'    prodDoc.Product.ApplyWorkMode DESIGN_MODE

    Dim subprods As Products
    Set subprods = prodDoc.Product.Products
    Set PartVolumePair = New Collection

    Dim i As Integer
    Dim partBodyPubl As Publication
    For i = 1 To subprods.Count

        On Error GoTo NoPartBody
        Set partBodyPubl = subprods.Item(i).Publications.Item("PartBody")
        PhysicalPartComboBox.AddItem subprods.Item(i).PartNumber
NoPartBody:
        On Error GoTo 0

        LogicalPartComboBox.AddItem subprods.Item(i).PartNumber
        PartVolumePair.Add subprods.Item(i).ReferenceProduct.Parent, subprods.Item(i).PartNumber
    Next i

    ' Hard coded list of supported primitives
    Set listOfPrimitives = New Collection
    listOfPrimitives.Add "G4Box"
    listOfPrimitives.Add "G4Cons"
    listOfPrimitives.Add "G4Tubs"
    listOfPrimitives.Add "G4Sphere"

    cmbInsert.Enabled = False
    
End Sub

Private Sub cmbInsert_Click()

    ' GUI
    lblStatus.Caption = "The replica is being created. Please, wait."

    ' Do "coincidence standard planes" if switched on
    If chkCSP.Value = True Then Call coincidence_std_planes

    Dim ProductDoc As ProductDocument
    Set ProductDoc = CATIA.ActiveDocument

    ' Find the publication to be copied
    Dim pub As Publication
    Dim i As Integer
    For i = 1 To ProductDoc.Product.Products.Count
        If (ProductDoc.Product.Products.Item(i).PartNumber = PhysicalPartComboBox.Text) Then
            Set pub = ProductDoc.Product.Products.Item(i).Publications.Item("PartBody")
            Exit For
        End If
    Next i

    Dim partDoc As PartDocument
    Set partDoc = PartVolumePair.Item(LogicalPartComboBox.Text)

    ' Copy - paste - as result with link
    Dim sel As Selection
    Set sel = CATIA.ActiveDocument.Selection
    sel.Clear
    sel.Add pub
    sel.Copy
    sel.Clear
    sel.Add partDoc.Part
    sel.PasteSpecial "CATPrtResult"
    sel.Clear
    
    ' Rename recent copied body
    partDoc.Part.Bodies.Item(partDoc.Part.Bodies.Count).Name = txtGenName.Text
    ' Generate transformations with corresponding offset
    generateTransformations partDoc
    ' Generate pattern
    generatePattern partDoc

    ' Update
    partDoc.Part.Update

    Call nameGenerate
    
    ' GUI
    lblStatus.Caption = "The replica is created." + vbNewLine + "Press 'Exit' to finish or fill all the fields and press 'Create' button."

End Sub

Private Sub nameGenerate()

    If (PhysicalPartComboBox.Text = LogicalPartComboBox.Text) Then
        MsgBox "You have selected the same part twice.", vbExclamation, "Attention"
        txtGenName.Text = ""
        cmbInsert.Enabled = False
        Exit Sub
    End If
    
    Dim ProductDoc As ProductDocument
    Dim partDoc As PartDocument
    Set ProductDoc = CATIA.ActiveDocument
    Set partDoc = PartVolumePair.Item(LogicalPartComboBox.Text)

    Dim i As Integer
    Dim maxIndex As Integer
    Dim prefixLine As String
    Dim indexLine As String
    maxIndex = 0
    prefixLine = "Body." + PhysicalPartComboBox.Text + "."
    For i = 1 To partDoc.Part.Bodies.Count
        If (StrComp(Mid(partDoc.Part.Bodies.Item(i).Name, 1, Len(prefixLine)), prefixLine, vbTextCompare) = 0) Then
            indexLine = Mid(partDoc.Part.Bodies.Item(i).Name, Len(prefixLine) + 1)
            If ((CommonDigitalString.isNum(indexLine) = True) And (Val(indexLine) > maxIndex)) Then
                maxIndex = Val(indexLine)
            End If
        End If
    Next

    txtGenName.Text = prefixLine & (maxIndex + 1)
    cmbInsert.Enabled = True

End Sub

Private Sub cmbCancel_Click()

    End
    
End Sub
