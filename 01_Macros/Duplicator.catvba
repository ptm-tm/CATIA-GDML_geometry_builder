Attribute VB_Name = "Duplicator"
Sub CATMain()

    formDuplicator.Show vbModeless

End Sub

Attribute VB_Name = "formDuplicator"
Attribute VB_Base = "0{FD78ECD3-8D64-4E67-8822-04ACCDD1CDC7}{301A03EF-6368-4C87-BAED-AC62B395577A}"
Attribute VB_GlobalNameSpace = False
Attribute VB_Creatable = False
Attribute VB_PredeclaredId = True
Attribute VB_Exposed = False
Attribute VB_TemplateDerived = False
Attribute VB_Customizable = False
Option Explicit

Private Sub cmbDuplicate_Click()

    CATIA.DisplayFileAlerts = False

    Dim docs As Documents
    Set docs = CATIA.Documents

    Dim topProdDoc As ProductDocument
    Set topProdDoc = CATIA.ActiveDocument

    Dim topProd As Product
    Set topProd = topProdDoc.Product

    Dim prods As Variant
    Set prods = topProd.Products

    Dim i As Integer
    Dim j As Integer
    Dim k As Integer
    Dim currentIndex As Integer
    Dim suffix As String
    Dim fullFilename As String
    Dim originalName As String
    Dim newFileName As String

    Dim tmpStr As String
    Dim volumeName As String
    Dim pos As Integer
    
    Dim ppath As String
    
    
    Dim originalNamesList() As String
    ReDim originalNamesList(ListBox1.ListCount)
    
    For i = 0 To ListBox1.ListCount - 1
        If (ListBox1.Selected(i)) Then
            fullFilename = ListBox1.List(i)
            originalName = Left(fullFilename, Len(fullFilename) - 8)
            pos = InStrRev(originalName, "\")
            originalNamesList(i) = Mid(originalName, pos + 1)
        End If
    Next i
    
    
    For currentIndex = 1 To Val(txtAmount.Text)

        suffix = ListBox2.List(currentIndex - 1) + "_"
    
        For i = 0 To ListBox1.ListCount - 1
        
            If (ListBox1.Selected(i)) Then
                fullFilename = ListBox1.List(i)
                originalName = Left(fullFilename, Len(fullFilename) - 8)

                pos = InStrRev(originalName, "\")
                volumeName = Mid(originalName, pos + 1)
                ppath = Left(originalName, pos)
               
                newFileName = ppath + suffix + volumeName + ".CATPart"
                
                'ListBox2.AddItem newFileName

                Dim newPartDoc As PartDocument
                Set newPartDoc = docs.NewFrom(fullFilename)
                newPartDoc.Product.PartNumber = suffix + volumeName
                newPartDoc.SaveAs newFileName

                Dim prt As Part
                Set prt = newPartDoc.Part

                Dim bds As Bodies
                Dim bd As Body
                Dim sol As Solid
                'Dim srcProd As Product
                Dim toChange As Boolean

                Set bds = prt.Bodies
                
                For j = 1 To bds.Count
                    Set bd = bds.Item(j)
                    If (bd.Shapes.Count > 1) Then
                    
                        Set sol = bd.Shapes.Item(1)
                    
                        If (Left(sol.Name, 8) = "Assemble") Then
                        
                        Else
                            'Set srcProd = sol.SourceProduct
    
                            ' set the name of the body to the new
                            Dim refName As String
                            Dim postfix As String
                            pos = InStrRev(bd.Name, ".")
                            postfix = Mid(bd.Name, pos)
                            refName = Mid(bd.Name, 6, pos - 6)
                            
                            toChange = False
                            For k = 0 To ListBox1.ListCount - 1
                                If (originalNamesList(k) = refName) Then
                                    toChange = True
                                End If
                            Next k
                            
                            If (toChange = True) Then
                                bd.Name = "Body." + suffix + refName + postfix
                            Else
                                bd.Name = "Body." + refName + postfix
                            End If
    
                            ' set the correct reference
                            'ListBox2.AddItem refName + " : " + srcProd.Name

                        End If

                    End If
                Next j

                Dim arrayOfVariantOfBSTR1(0)
                arrayOfVariantOfBSTR1(0) = newFileName
                prods.AddComponentsFromFiles arrayOfVariantOfBSTR1, "All"

            End If
        
        Next i

    Next currentIndex

    CATIA.DisplayFileAlerts = True

End Sub

Private Sub cmbExit_Click()

    End

End Sub

Private Sub cmbParam_Click()

    Dim topProdDoc As ProductDocument
    Dim topProd As Product
    Set topProdDoc = CATIA.ActiveDocument
    Set topProd = topProdDoc.Product

    Dim params As Parameters
    Dim rels As Relations

    Set params = topProd.Parameters
    Set rels = topProd.Relations


    Dim currentIndex As Integer
    Dim suffix As String
    Dim i As Integer
    Dim j As Integer
    Dim oldParamName As String
    Dim oldParam As Parameter
    Dim newParamName As String
    Dim oldParamVal As Double
    Dim newFormula As String


    Dim pos As Integer
    Dim fullFilename As String
    Dim originalName As String
    Dim originalNamesList() As String
    ReDim originalNamesList(ListBox1.ListCount)
    
    For i = 0 To ListBox1.ListCount - 1
        If (ListBox1.Selected(i)) Then
            fullFilename = ListBox1.List(i)
            originalName = Left(fullFilename, Len(fullFilename) - 8)
            pos = InStrRev(originalName, "\")
            originalNamesList(i) = Mid(originalName, pos + 1)
        End If
    Next i

    ' Iterations over new instances
    For currentIndex = 1 To Val(txtAmount.Text)

        suffix = ListBox2.List(currentIndex - 1) + "_"
    
        ' Generating new control parameters
        For i = 0 To lstRenamedParams.ListCount - 1

            ' Only if the parameter is 'renamed' (meaning user-defined)
            If (lstRenamedParams.Selected(i)) Then

                ' Get the original name, generate the new name
                oldParamName = lstRenamedParams.List(i)
                newParamName = suffix + oldParamName

                ' Get the value of the original parameter
                Set oldParam = params.GetItem(oldParamName)
                oldParamVal = Val(oldParam.ValueAsString)

                ' Create the new parameter
                params.CreateReal newParamName, oldParamVal

                ' Add to the list (for debug)
                lstRenamedParamsNew.AddItem newParamName

            End If

        Next i

        Dim curFormula As String
        Dim newRelationName As String

        ' Loop over the selected element of the generated list of relations
        For j = 0 To lstRelationNames.ListCount - 1
            If (lstRelationNames.Selected(j)) Then
                ' Generate new name of the relation
                newRelationName = suffix + lstRelationNames.List(j)
                lstRelationNamesNew.AddItem newRelationName

                ' Generate new right side of the formula
                curFormula = lstRelFormulas.List(j)
                For i = 0 To lstRenamedParams.ListCount - 1
                    If (lstRenamedParams.Selected(i)) Then
                        oldParamName = lstRenamedParams.List(i)
                        newParamName = suffix + oldParamName
                        curFormula = Replace(curFormula, oldParamName, newParamName)
                    End If
                Next i
                lstRelFormulasNew.AddItem curFormula

                ' TODO FIXME
                ' 10aug2015 !!!!!!!!!!!!!!!!!!!!!!!!!!!!!!!!!!!!!!!!!!!
                ' Generate new left side of the formula (reuse variables oldParamName, oldParam)
                oldParamName = lstRelParams.List(j)
                For i = 0 To lstVolNames.ListCount - 1
                    If (ListBox1.Selected(i)) Then
                        oldParamName = Replace(oldParamName, lstVolNames.List(i) + "\", suffix + lstVolNames.List(i) + "\")
                        oldParamName = Replace(oldParamName, lstVolNames.List(i) + ".", suffix + lstVolNames.List(i) + ".")
                    End If
                Next i

                lstRelParamsNew.AddItem oldParamName
                Set oldParam = params.GetItem(oldParamName)

                ' Create the relation with name 'newRelationName' for parameter 'oldParamName' with formula 'curFormula'
                rels.CreateFormula newRelationName, "AutoGenerated", oldParam, curFormula

            End If
        Next j

    Next currentIndex

End Sub

Private Sub CommandButton1_Click()

    Dim filenum As Integer
    Dim filename As String
    Dim dataline As String
    
    filenum = FreeFile()
    filename = TextBox1.Text
    
    Open filename For Input As #filenum
    
    While Not EOF(filenum)
        Line Input #filenum, dataline
        ListBox2.AddItem dataline
    Wend
    
    txtAmount.Text = Trim(Str(ListBox2.ListCount))

End Sub

Private Sub UserForm_Initialize()

    Dim docs As Documents
    Set docs = CATIA.Documents

    Dim i As Integer
    Dim prtDoc As PartDocument

    Dim originalName As String
    Dim pos As Integer
    Dim volName As String

    ' List all the loaded documents
    For i = 1 To docs.Count
        If (TypeName(docs.Item(i)) = "PartDocument") Then
            Set prtDoc = docs.Item(i)

            ' List the name of the file
            ListBox1.AddItem prtDoc.FullName

            ' Extract the name of the volume
            originalName = Left(prtDoc.FullName, Len(prtDoc.FullName) - 8)
            pos = InStrRev(originalName, "\")
            volName = Mid(originalName, pos + 1)

            ' List the name of the volume
            lstVolNames.AddItem volName
        End If
    Next i

    Dim topProdDoc As ProductDocument
    Dim topProd As Product
    Set topProdDoc = CATIA.ActiveDocument
    Set topProd = topProdDoc.Product

    Dim params As Parameters
    Set params = topProd.Parameters

    Dim param As Parameter
    Dim rel As Relation

    ' Loop over the parameters
    For i = 1 To params.Count
        Set param = params.Item(i)

        ' Just find and list renamed (user-defined) parameters - our control parameters
        If (param.Renamed And param.Name <> "Material") Then
            lstRenamedParams.AddItem param.Name ' + " = " + param.ValueAsString
            lstParamValues.AddItem param.ValueAsString
        End If

        ' Find and list parameters with formulas - indicate their formulas
        If (Not (param.OptionalRelation Is Nothing)) Then
            Set rel = param.OptionalRelation
            lstRelationNames.AddItem rel.Name
            lstRelParams.AddItem param.Name
            lstRelFormulas.AddItem rel.Value
        End If
    Next i

End Sub
