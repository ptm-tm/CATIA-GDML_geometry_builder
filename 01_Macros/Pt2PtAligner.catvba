Attribute VB_Name = "Pt2PtAligner"
Sub CATMain()

    ' Language
    Dim builderLanguage As String
    builderLanguage = CATIA.SystemService.Environ("BuilderLanguage")
    If builderLanguage = "" Then builderLanguage = "English"

    ' GUI
    Select Case builderLanguage
    Case "English":
        formPt2PtAligner.Caption = "Point to point aligner"
        formPt2PtAligner.cmbExit.Caption = "Exit"
        formPt2PtAligner.cmbPick.Caption = "Pick points"
        formPt2PtAligner.ToggleButton1.Caption = "Show additional info"
        formPt2PtAligner.lblComp.Caption = "Components:"
        formPt2PtAligner.lblD.Caption = "Distance:"
        formPt2PtAligner.lblP1.Caption = "Point1:"
        formPt2PtAligner.lblP2.Caption = "Point2:"
        formPt2PtAligner.lblStatus.Caption = "Press 'Pick points' to start"

    Case "Russian":
        formPt2PtAligner.Caption = "Точка к точке"
        formPt2PtAligner.cmbExit.Caption = "Выход"
        formPt2PtAligner.cmbPick.Caption = "Выбрать точки"
        formPt2PtAligner.ToggleButton1.Caption = "Показать дополнительн. информацию"
        formPt2PtAligner.lblComp.Caption = "Компоненты:"
        formPt2PtAligner.lblD.Caption = "Расстояние:"
        formPt2PtAligner.lblP1.Caption = "Точка1:"
        formPt2PtAligner.lblP2.Caption = "Точка2:"
        formPt2PtAligner.lblStatus.Caption = "Нажмите 'Выбрать точки' чтобы начать"

    End Select

    ' Show form
    formPt2PtAligner.Show vbModeless

End Sub

Attribute VB_Name = "formPt2PtAligner"
Attribute VB_Base = "0{82047095-1CB2-4177-A7EB-7A05A1AB5118}{903EC813-51C3-4A63-A861-7A4051B30956}"
Attribute VB_GlobalNameSpace = False
Attribute VB_Creatable = False
Attribute VB_PredeclaredId = True
Attribute VB_Exposed = False
Attribute VB_TemplateDerived = False
Attribute VB_Customizable = False
Option Explicit

Dim AFormMethodIsBeingExecuted As Boolean

Private Sub cmbPick_Click()

    ' Language
    Dim builderLanguage As String
    builderLanguage = CATIA.SystemService.Environ("BuilderLanguage")

    Dim prtDoc As PartDocument
    Dim prodDoc As ProductDocument
    Dim sel
    Dim inpObjType(0)
    Dim lin1
    Dim lin2
    Dim hybShpRef1 As Reference
    Dim hybShpRef2 As Reference
    Dim TheSPAWorkbench As Workbench
    Dim Measure1 'As Measurable
    Dim Measure2 'As Measurable
    Dim stat
    Dim i As Integer

    If TypeName(CATIA.ActiveDocument) = "PartDocument" Then
        Set prtDoc = CATIA.ActiveDocument
        Set sel = prtDoc.Selection
        Set TheSPAWorkbench = prtDoc.GetWorkbench("SPAWorkbench")
    ElseIf TypeName(CATIA.ActiveDocument) = "ProductDocument" Then
        Set prodDoc = CATIA.ActiveDocument
        Set sel = prodDoc.Selection
        Set TheSPAWorkbench = prodDoc.GetWorkbench("SPAWorkbench")
    End If

    ' GUI
    lst1.Clear
    txtD.Text = ""
    txtP1.Text = ""
    txtP2.Text = ""

    inpObjType(0) = "Vertex"

    ' Select the first point

    ' GUI
    Select Case builderLanguage
    Case "English":
        formPt2PtAligner.lblStatus.Caption = "Choose the first geometric element (point) in the geometry area"
    Case "Russian":
        formPt2PtAligner.lblStatus.Caption = "Выберете первый геометрический элемент (точку) в области геометрии"
    End Select

    AFormMethodIsBeingExecuted = True
    stat = sel.SelectElement2(inpObjType, "Select a vertex", False)
    AFormMethodIsBeingExecuted = False

    If (stat = "Normal") Then
        Set lin1 = sel.Item2(1)
        Set hybShpRef1 = lin1.Reference
        Set Measure1 = TheSPAWorkbench.GetMeasurable(hybShpRef1)
        txtP1.Text = hybShpRef1.DisplayName
    Else
        End
    End If

    ' Select the second point

    ' GUI
    Select Case builderLanguage
    Case "English":
        formPt2PtAligner.lblStatus.Caption = "Choose the second geometric element (point) in the geometry area"
    Case "Russian":
        formPt2PtAligner.lblStatus.Caption = "Выберете второй геометрический элемент (точку) в области геометрии"
    End Select

    AFormMethodIsBeingExecuted = True
    stat = sel.SelectElement2(inpObjType, "Select a vertex", False)
    AFormMethodIsBeingExecuted = False

    If (stat = "Normal") Then
        Set lin2 = sel.Item2(1)
        Set hybShpRef2 = lin2.Reference
        Set Measure2 = TheSPAWorkbench.GetMeasurable(hybShpRef2)
        txtP2.Text = hybShpRef2.DisplayName
    Else
        End
    End If

    ' Do measurement
    Dim arr(5)
    txtD.Text = Measure2.GetMinimumDistance(hybShpRef1)
    Measure2.GetMinimumDistancePoints hybShpRef1, arr

    For i = 0 To 2
        lst1.AddItem Round(arr(i) - arr(i + 3), 10)
    Next i

    Dim g4udffeat
    Dim g4udffeattype As String
    Set g4udffeat = hybShpRef1.Parent
    g4udffeattype = TypeName(g4udffeat)

    Dim g4udftrans As HybridShapeTranslate

    Dim shps As Shapes
    Dim trFound As Boolean

    Select Case g4udffeattype
        Case "HybridShapeTranslate"
            Set g4udftrans = hybShpRef1.Parent
            trFound = True
        Case "CircPattern"
            ' Replica or array case - the last feature is not translation, but pattern
            ' Seek for translation feature in the shapes list. If not found - critical error
            Set shps = hybShpRef1.Parent.Parent

            trFound = False
            For i = 1 To shps.Count
                If Left(shps.Item(i).Name, 10) = "Translate." Then
                    Set g4udftrans = shps.Item(i)
                    trFound = True
                    Exit For
                End If
            Next i

            Select Case builderLanguage
            Case "English":
                MsgBox "Please, note that for circular pattern (array or replica) it is practically " + _
                    "impossible to find a translation to satisfy arbitrary position of an element. " + _
                    "Result may not be correct.", vbExclamation
            Case "Russian":
                MsgBox "Обратите внимание, что в случае кругового множественного позиционирования " + _
                    "(array или replica) практически невозможно рассчитать смещение, " + _
                    "удовлетворяющее произвольному положению выбранного элемента массива. " + _
                    "Результат операции может быть непредсказуемым.", vbExclamation
            End Select

        Case "RectPattern"
            ' Replica or array case - the last feature is not translation, but pattern
            ' Seek for translation feature in the shapes list. If not found - critical error
            Set shps = hybShpRef1.Parent.Parent

            trFound = False
            For i = 1 To shps.Count
                If Left(shps.Item(i).Name, 10) = "Translate." Then
                    Set g4udftrans = shps.Item(i)
                    trFound = True
                    Exit For
                End If
            Next i
    End Select

    ' Apply
    If trFound = True Then
    
#If VBA7 Then
        g4udftrans.CoordXValue = g4udftrans.CoordXValue + Round(arr(0) - arr(0 + 3), 10)
        g4udftrans.CoordYValue = g4udftrans.CoordYValue + Round(arr(1) - arr(1 + 3), 10)
        g4udftrans.CoordZValue = g4udftrans.CoordZValue + Round(arr(2) - arr(2 + 3), 10)
#Else
        g4udftrans.CoordXValue = g4udftrans.CoordXValue + Round(arr(0) - arr(0 + 3), 10) / 1000#
        g4udftrans.CoordYValue = g4udftrans.CoordYValue + Round(arr(1) - arr(1 + 3), 10) / 1000#
        g4udftrans.CoordZValue = g4udftrans.CoordZValue + Round(arr(2) - arr(2 + 3), 10) / 1000#
#End If

    Else

        Select Case builderLanguage
        Case "English":
            MsgBox "Translation feature not found. Aborting", vbCritical
        Case "Russian":
            MsgBox "Формообразование смещения (Translation) на найдено. Операция прервана", vbCritical
        End Select

        End
    End If

    ' Update
    If Right(CATIA.ActiveDocument.Name, 8) = ".CATPart" Then
        prtDoc.Part.Update
    ElseIf Right(CATIA.ActiveDocument.Name, 11) = ".CATProduct" Then
        prodDoc.Product.Update
    End If

    ' GUI
    Select Case builderLanguage
    Case "English":
        formPt2PtAligner.lblStatus.Caption = "Press 'Pick points' to start"
    Case "Russian":
        formPt2PtAligner.lblStatus.Caption = "Нажмите 'Выбрать точки' чтобы начать"
    End Select

End Sub

Private Sub ToggleButton1_Click()

    If ToggleButton1.Value = True Then
        formPt2PtAligner.Height = 468
    Else
        formPt2PtAligner.Height = 178
    End If

End Sub

Private Sub cmbExit_Click()

    End

End Sub
