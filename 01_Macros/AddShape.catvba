Attribute VB_Name = "AddShape"
Sub CATMain()

    formAddShape.Show vbModeless
    
End Sub

Attribute VB_Name = "Support"
Option Explicit

' Update Nov2016 - change rotation order to XYZ

Sub AddRotates(destPart As Part, bd As Body)

    Dim hybShpFactory As HybridShapeFactory
    Dim shpFactory As ShapeFactory
    Dim origin As OriginElements
    Dim refPlaneXY As Reference
    Dim refPlaneYZ As Reference
    Dim refPlaneZX As Reference
    Dim sel As Selection
    Dim visPropSet As VisPropertySet
    
    Set hybShpFactory = destPart.HybridShapeFactory
    Set shpFactory = destPart.ShapeFactory
    Set origin = destPart.OriginElements
    Set refPlaneXY = destPart.CreateReferenceFromObject(origin.PlaneXY)
    Set refPlaneYZ = destPart.CreateReferenceFromObject(origin.PlaneYZ)
    Set refPlaneZX = destPart.CreateReferenceFromObject(origin.PlaneZX)
    Set sel = CATIA.ActiveDocument.Selection
    Set visPropSet = sel.VisProperties

    Dim Intersection_XY_ZX As HybridShapeIntersection
    Dim Intersection_YZ_XY As HybridShapeIntersection
    Dim Intersection_ZX_YZ As HybridShapeIntersection

    'X axis preparation
    Set Intersection_XY_ZX = hybShpFactory.AddNewIntersection(refPlaneXY, refPlaneZX)
    Intersection_XY_ZX.PointType = 0
    bd.InsertHybridShape Intersection_XY_ZX
    destPart.InWorkObject = Intersection_XY_ZX
    Intersection_XY_ZX.Name = "X axis"
    sel.Clear
    sel.Add Intersection_XY_ZX
    visPropSet.SetShow catVisPropertyNoShowAttr
    sel.Clear
'    destPart.Update
    'Y axis preparation
    Set Intersection_YZ_XY = hybShpFactory.AddNewIntersection(refPlaneYZ, refPlaneXY)
    Intersection_YZ_XY.PointType = 0
    bd.InsertHybridShape Intersection_YZ_XY
    destPart.InWorkObject = Intersection_YZ_XY
    Intersection_YZ_XY.Name = "Y axis"
    sel.Clear
    sel.Add Intersection_YZ_XY
    visPropSet.SetShow catVisPropertyNoShowAttr
    sel.Clear
'    destPart.Update
    'Z axis preparation
    Set Intersection_ZX_YZ = hybShpFactory.AddNewIntersection(refPlaneZX, refPlaneYZ)
    Intersection_ZX_YZ.PointType = 0
    bd.InsertHybridShape Intersection_ZX_YZ
    destPart.InWorkObject = Intersection_ZX_YZ
    Intersection_ZX_YZ.Name = "Z axis"
    sel.Clear
    sel.Add Intersection_ZX_YZ
    visPropSet.SetShow catVisPropertyNoShowAttr
    sel.Clear
'    destPart.Update

    Dim refAxisX As Reference
    Dim refAxisY As Reference
    Dim refAxisZ As Reference
    Dim hybShpRotX As HybridShapeRotate
    Dim hybShpRotY As HybridShapeRotate
    Dim hybShpRotZ As HybridShapeRotate
    Dim rotX As Rotate
    Dim rotY As Rotate
    Dim rotZ As Rotate

    'Rotate by X axis creation
    Set refAxisX = destPart.CreateReferenceFromObject(Intersection_XY_ZX)
    Set rotX = shpFactory.AddNewRotate2(refAxisX, 0)
    Set hybShpRotX = rotX.HybridShape
    hybShpRotX.RotationType = 0
    hybShpRotX.Axis = refAxisX
    hybShpRotX.Name = "Rotate.X"
'    destPart.InWorkObject = hybShpRotX
'    destPart.Update
    'Rotate by Y axis creation
    Set refAxisY = destPart.CreateReferenceFromObject(Intersection_YZ_XY)
    Set rotY = shpFactory.AddNewRotate2(refAxisY, 0)
    Set hybShpRotY = rotY.HybridShape
    hybShpRotY.RotationType = 0
    hybShpRotY.Axis = refAxisY
    hybShpRotY.Name = "Rotate.Y"
'    destPart.InWorkObject = hybShpRotY
'    destPart.Update
    'Rotate by Z axis creation
    Set refAxisZ = destPart.CreateReferenceFromObject(Intersection_ZX_YZ)
    Set rotZ = shpFactory.AddNewRotate2(refAxisZ, 0)
    Set hybShpRotZ = rotZ.HybridShape
    hybShpRotZ.RotationType = 0
    hybShpRotZ.Axis = refAxisZ
    hybShpRotZ.Name = "Rotate.Z"
'    destPart.InWorkObject = hybShpRotZ
'    destPart.Update

    ' Update
'    destPart.Update
 
End Sub
                
Sub AddTranslate(destPart As Part, bd As Body)

    Dim shpFactory As ShapeFactory
    Dim trans As Translate
    Dim hybShpTrans As HybridShapeTranslate

    Set shpFactory = destPart.ShapeFactory
    Set trans = shpFactory.AddNewTranslate2(0)
    Set hybShpTrans = trans.HybridShape

    hybShpTrans.VectorType = 2
    hybShpTrans.CoordXValue = 0#
    hybShpTrans.CoordYValue = 0#
    hybShpTrans.CoordZValue = 0#
'    destPart.InWorkObject = hybShpTrans

    ' Update
'    destPart.Update

End Sub

Attribute VB_Name = "formAddShape"
Attribute VB_Base = "0{4EAA5F9E-C2D5-4EB3-B138-419E8FC16B5A}{B88CF69B-49D7-4F6F-853A-D70C9520F40A}"
Attribute VB_GlobalNameSpace = False
Attribute VB_Creatable = False
Attribute VB_PredeclaredId = True
Attribute VB_Exposed = False
Attribute VB_TemplateDerived = False
Attribute VB_Customizable = False
Option Explicit

Dim shapeFolderStr As String
Dim AFormMethodIsBeingExecuted As Boolean

Private Sub UserForm_Initialize()

    'Is active document a part?
    If (TypeName(CATIA.ActiveDocument) <> "PartDocument") Then
        MsgBox "The type of the active document must be a part", vbCritical, "AddShape"
        End
    End If
    
    shapeFolderStr = CATIA.SystemService.Environ("BuilderPath") & "\02_Elements"
    
    If CATIA.FileSystem.FolderExists(shapeFolderStr) = False Then
        MsgBox "Shape folder '" & shapeFolderStr & "' does not exist. Check 'BuilderPath' environment variable.", vbCritical, "AddShape"
        End
    End If
    
    Dim shapeFolder As Folder
    Dim shapeFiles As Files
    Set shapeFolder = CATIA.FileSystem.GetFolder(shapeFolderStr)
    Set shapeFiles = shapeFolder.Files
    
    Dim i_file As Integer
    For i_file = 1 To shapeFiles.Count
        If (Right(shapeFiles.Item(i_file).Name, 8) = ".CATPart") Then
            lstPrimitives.AddItem shapeFiles.Item(i_file).Name
        End If
    Next i_file

    lstPrimitives.ListIndex = 1

End Sub

Private Sub lstPrimitives_DblClick(ByVal Cancel As MSForms.ReturnBoolean)

    Call cmbAdd_Click

End Sub

Private Sub cmbAdd_Click()

    Dim PartDest As Part
    Set PartDest = CATIA.ActiveDocument.Part
    
    If (TypeName(PartDest.InWorkObject) <> "Body") Then
        MsgBox "Please, activate a body to add shape" + vbNewLine + "(use 'Define In Work Object' in context menu of the body)"
        Exit Sub
    End If

    Dim bd As Body
    Set bd = PartDest.InWorkObject

    Dim i_shape As Integer
    i_shape = lstPrimitives.ListIndex

    Dim InsFactory As InstanceFactory
    Set InsFactory = PartDest.GetCustomerFactory("InstanceFactory")

    Dim YZPlane As Object
    Dim ZXPlane As Object
    Dim XYPlane As Object
    Set YZPlane = PartDest.FindObjectByName("yz plane")
    Set ZXPlane = PartDest.FindObjectByName("zx plane")
    Set XYPlane = PartDest.FindObjectByName("xy plane")

    Dim shapeName As String
    shapeName = Left(lstPrimitives.List(i_shape), Len(lstPrimitives.List(i_shape)) - 8)

    Call InsFactory.BeginInstanceFactory(shapeName, (shapeFolderStr & "\" & lstPrimitives.List(i_shape)))
    InsFactory.BeginInstantiate

    Dim sel
    Set sel = CATIA.ActiveDocument.Selection
    sel.Clear
    Dim inpObjType(0)
    inpObjType(0) = "Sketch"
    Dim stat


    Select Case shapeName
    Case "G4Box", "G4EllipticalTube", "G4Hedra", "G4Trd", "G4TwistedBox", "G4TwistedTrd", "G4TwistedTubs", "G4Arb8_2"
        InsFactory.PutInputData "xy plane", XYPlane
    Case "G4Cons", "G4Orb", "G4Sphere", "G4Sphere", "G4Tubs", "G4Torus"
        InsFactory.PutInputData "zx plane", ZXPlane
    Case "G4EllipticalCone"
        InsFactory.PutInputData "yz plane", YZPlane
        InsFactory.PutInputData "zx plane", ZXPlane
    Case "G4Para", "G4Trap", "G4TwistedTrap"
        InsFactory.PutInputData "zx plane", ZXPlane
        InsFactory.PutInputData "xy plane", XYPlane
    Case "G4Ellipsoid"
        InsFactory.PutInputData "yz plane", YZPlane
        InsFactory.PutInputData "zx plane", ZXPlane
        InsFactory.PutInputData "xy plane", XYPlane
    Case "G4Xtru2sec"
        AFormMethodIsBeingExecuted = True
        stat = sel.SelectElement2(inpObjType, "Select a sketch", False)
        AFormMethodIsBeingExecuted = False
        If (stat = "Normal") Then
            Dim blueprintSketch As Sketch
            Set blueprintSketch = sel.Item2(1).Value
            InsFactory.PutInputData "Blueprint", blueprintSketch
        Else
            'TODO exception
            MsgBox "Sketch selection gone wrong. Aborting.", vbCritical
            End
        End If
    Case Else
        MsgBox "Shape " & shapeName & " is not implemented"
        Exit Sub
    End Select

    InsFactory.Instantiate
    InsFactory.EndInstantiate
    InsFactory.EndInstanceFactory

    If CheckBoxRots.Value = True Then
        AddRotates PartDest, bd
    End If

    If CheckBoxTrans.Value = True Then
        AddTranslate PartDest, bd
    End If

    CATIA.ActiveDocument.Part.Update

    End

End Sub

Private Sub cmbExit_Click()

    End

End Sub
