Attribute VB_Name = "Poly"
Sub CATMain()

    formPoly.Show

End Sub

Attribute VB_Name = "Support"
Option Explicit

Public Function CreateHedra(path As String, _
                    PartDocumentDest As PartDocument, _
                    pRmin1 As String, _
                    pRmax1 As String, _
                    pRmin2 As String, _
                    pRmax2 As String, _
                    pDz As String, _
                    pSPhi As String, _
                    pDPhi As String, _
                    numSide As String, _
                    lunit As String, _
                    aunit As String, _
                    isForPolyhedra As Boolean) As Body

    Dim PartDest As Part
    Dim InsFactory As InstanceFactory
    Dim MyInstance 'As HybridShapeInstance
    Set PartDest = PartDocumentDest.Part
    
    If isForPolyhedra = False Then
        Set CreateHedra = PartDest.Bodies.Add
        PartDest.InWorkObject = CreateHedra
    End If
    
    Set InsFactory = PartDest.GetCustomerFactory("InstanceFactory")
    
    Dim XYPlane As Object
    Dim param1 As Parameter
    Dim param2 As Parameter
    Dim param3 As Parameter
    Dim param4 As Parameter
    Dim param5 As Parameter
    Dim param6 As Parameter
    Dim param7 As Parameter
    Dim param8 As Parameter
    
    Call InsFactory.BeginInstanceFactory("G4Hedra", (path & "\G4Hedra.CATPart"))
    InsFactory.BeginInstantiate
    
    Set XYPlane = PartDest.FindObjectByName("xy plane")
    InsFactory.PutInputData "xy plane", XYPlane
    
    Set param1 = InsFactory.GetParameter("pRmin1")
    Set param2 = InsFactory.GetParameter("pRmax1")
    Set param3 = InsFactory.GetParameter("pRmin2")
    Set param4 = InsFactory.GetParameter("pRmax2")
    Set param5 = InsFactory.GetParameter("pDz")
    Set param6 = InsFactory.GetParameter("pSPhi")
    Set param7 = InsFactory.GetParameter("pDPhi")
    Set param8 = InsFactory.GetParameter("numSide")
    
    param1.ValuateFromString (Str(Val(Trim(pRmin1)) * unitConvert(lunit)) & "mm")
    param2.ValuateFromString (Str(Val(Trim(pRmax1)) * unitConvert(lunit)) & "mm")
    param3.ValuateFromString (Str(Val(Trim(pRmin2)) * unitConvert(lunit)) & "mm")
    param4.ValuateFromString (Str(Val(Trim(pRmax2)) * unitConvert(lunit)) & "mm")
    param5.ValuateFromString (Str(Val(Trim(pDz)) * unitConvert(lunit)) & "mm")
    param6.ValuateFromString (Str(Val(Trim(pSPhi)) * unitConvert(aunit)) & "deg")
    param7.ValuateFromString (Str(Val(Trim(pDPhi)) * unitConvert(aunit)) & "deg")
    param8.ValuateFromString Str(Val(Trim(numSide)))
    
    Set MyInstance = InsFactory.Instantiate
    InsFactory.EndInstantiate
    InsFactory.EndInstanceFactory
    
    If isForPolyhedra = True Then
        MyInstance.Name = "PolyhedraPiece." & Mid(MyInstance.Name, 9)
    End If

End Function

Public Function CreateCons(path As String, _
                    PartDocumentDest As PartDocument, _
                    pRmin1 As String, _
                    pRmax1 As String, _
                    pRmin2 As String, _
                    pRmax2 As String, _
                    pDz As String, _
                    pSPhi As String, _
                    pDPhi As String, _
                    lunit As String, _
                    aunit As String, _
                    isForPolycone As Boolean) As Body

    Dim PartDest As Part
    Dim InsFactory As InstanceFactory
    Dim MyInstance 'As HybridShapeInstance
    Set PartDest = PartDocumentDest.Part
    
    If isForPolycone = False Then
        Set CreateCons = PartDest.Bodies.Add
        PartDest.InWorkObject = CreateCons
    End If
    
    Set InsFactory = PartDest.GetCustomerFactory("InstanceFactory")
    
    Dim ZXPlane As Object
    Dim param1 As Parameter
    Dim param2 As Parameter
    Dim param3 As Parameter
    Dim param4 As Parameter
    Dim param5 As Parameter
    Dim param6 As Parameter
    Dim param7 As Parameter
    
    Call InsFactory.BeginInstanceFactory("G4Cons", (path & "\G4Cons.CATPart"))
    InsFactory.BeginInstantiate
    
    Set ZXPlane = PartDest.FindObjectByName("zx plane")
    InsFactory.PutInputData "zx plane", ZXPlane
    
    Set param1 = InsFactory.GetParameter("pRmin1")
    Set param2 = InsFactory.GetParameter("pRmax1")
    Set param3 = InsFactory.GetParameter("pRmin2")
    Set param4 = InsFactory.GetParameter("pRmax2")
    Set param5 = InsFactory.GetParameter("pDz")
    Set param6 = InsFactory.GetParameter("pSPhi")
    Set param7 = InsFactory.GetParameter("pDPhi")
    
    param1.ValuateFromString (Str(Val(Trim(pRmin1)) * unitConvert(lunit)) & "mm")
    param2.ValuateFromString (Str(Val(Trim(pRmax1)) * unitConvert(lunit)) & "mm")
    param3.ValuateFromString (Str(Val(Trim(pRmin2)) * unitConvert(lunit)) & "mm")
    param4.ValuateFromString (Str(Val(Trim(pRmax2)) * unitConvert(lunit)) & "mm")
    param5.ValuateFromString (Str(Val(Trim(pDz)) * unitConvert(lunit)) & "mm")
    param6.ValuateFromString (Str(Val(Trim(pSPhi)) * unitConvert(aunit)) & "deg")
    param7.ValuateFromString (Str(Val(Trim(pDPhi)) * unitConvert(aunit)) & "deg")
    
    Set MyInstance = InsFactory.Instantiate
    InsFactory.EndInstantiate
    InsFactory.EndInstanceFactory
    
    If isForPolycone = True Then
        MyInstance.Name = "PolyconePiece." & Mid(MyInstance.Name, 8)
    End If

End Function

Public Sub CreateShift(PartDocumentDest As PartDocument, _
                        x As String, y As String, z As String, _
                        lunit As String)

    Dim hybShpFactory As HybridShapeFactory
    Dim shpFactory As ShapeFactory
    Dim hybShpTrans As HybridShapeTranslate
    Dim trans As Translate
    Set hybShpFactory = PartDocumentDest.Part.HybridShapeFactory
    Set shpFactory = PartDocumentDest.Part.ShapeFactory

    'Shift
    Set trans = shpFactory.AddNewTranslate2(0)
    Set hybShpTrans = trans.HybridShape
    hybShpTrans.VectorType = 2
    
'#If VBA7 Then
    
'    hybShpTrans.CoordXValue = Val(x) * unitConvert(lunit)
'    hybShpTrans.CoordYValue = Val(y) * unitConvert(lunit)
'    hybShpTrans.CoordZValue = Val(z) * unitConvert(lunit)
    
'#Else
    
    hybShpTrans.CoordXValue = Val(x) * unitConvert(lunit) / 1000#
    hybShpTrans.CoordYValue = Val(y) * unitConvert(lunit) / 1000#
    hybShpTrans.CoordZValue = Val(z) * unitConvert(lunit) / 1000#
    
'#End If
    
    hybShpTrans.Name = "Shift." & Mid(hybShpTrans.Name, 11)
    PartDocumentDest.Part.InWorkObject = hybShpTrans
    PartDocumentDest.Part.Update

End Sub

Public Function unitConvert(unit As String) As Double

    Dim PI As Double
    PI = 3.14159265358979
    Select Case unit
        Case "mm"
            unitConvert = 1#
        Case "cm"
            unitConvert = 10#
        Case "m"
            unitConvert = 1000#
        Case "deg"
            unitConvert = 1#
        Case "degree"
            unitConvert = 1#
        Case "radian"
            unitConvert = 180# / PI
        Case "rad"
            unitConvert = 180# / PI
    End Select

End Function

Attribute VB_Name = "formPoly"
Attribute VB_Base = "0{BB15C3D3-BAD6-44B7-873A-32C8FDE2B35B}{C7F0D14E-C55B-48A7-8DBF-BF9BA7B7307D}"
Attribute VB_GlobalNameSpace = False
Attribute VB_Creatable = False
Attribute VB_PredeclaredId = True
Attribute VB_Exposed = False
Attribute VB_TemplateDerived = False
Attribute VB_Customizable = False
Option Explicit

Dim pconDOMDoc As DOMDocument60
Dim pconXMLNode As IXMLDOMNode

Private Sub cmbAdd_Click()

    Dim newXMLNode As IXMLDOMNode
    Dim attr As IXMLDOMAttribute
    Set newXMLNode = pconDOMDoc.createElement("zplane")
    pconXMLNode.appendChild newXMLNode
    Set attr = pconDOMDoc.createAttribute("z")
    attr.Value = txtZ.Text
    newXMLNode.Attributes.setNamedItem attr
    Set attr = pconDOMDoc.createAttribute("rmin")
    attr.Value = txtRmin.Text
    newXMLNode.Attributes.setNamedItem attr
    Set attr = pconDOMDoc.createAttribute("rmax")
    attr.Value = txtRmax.Text
    newXMLNode.Attributes.setNamedItem attr
    
    ReorderList
    PrintList
    txtXMLBefore.Text = pconDOMDoc.xml
    
    txtZ.SetFocus
    txtZ.SelStart = 0
    txtZ.SelLength = Len(txtZ.Text)

End Sub

Private Sub PrintList()

    lstZplanes.Clear
    Dim j As Integer
    For j = 0 To (pconXMLNode.childNodes.Length - 1)
        lstZplanes.AddItem "zplane z=" & pconXMLNode.childNodes.Item(j).Attributes.getNamedItem("z").nodeValue & _
                            " rmin=" & pconXMLNode.childNodes.Item(j).Attributes.getNamedItem("rmin").nodeValue & _
                            " rmax=" & pconXMLNode.childNodes.Item(j).Attributes.getNamedItem("rmax").nodeValue
    Next j

End Sub

Private Sub ReorderList()

' reorder list so that it will be increasing z

    Dim i As Integer
    Dim j As Integer

    Dim cur_z As Double
    Dim cur_min As Double
    Dim cur_threshold As Double
    Dim cur_min_index As Integer
    Dim cur_min_node As IXMLDOMNode

    For j = 0 To (pconXMLNode.childNodes.Length - 1)
        cur_min = Val(pconXMLNode.childNodes.Item(0).Attributes.getNamedItem("z").nodeValue)
        cur_min_index = 0
        For i = 0 To (pconXMLNode.childNodes.Length - j - 1)
            cur_z = Val(pconXMLNode.childNodes.Item(i).Attributes.getNamedItem("z").nodeValue)
            If (cur_z < cur_min) Then
                If (j = 0) Then
                    cur_min = cur_z
                    cur_min_index = i
                Else
                    If (j > 0) Then
                        cur_min = cur_z
                        cur_min_index = i
                    End If
                End If
            End If
        Next i
        Set cur_min_node = pconXMLNode.childNodes.Item(cur_min_index)
        pconXMLNode.RemoveChild cur_min_node
        pconXMLNode.appendChild cur_min_node
    Next j

End Sub

Private Sub cmbCreate_Click()

    lblStatus.Caption = "The poly-primitive is being created. Please, wait."

    Dim prtDoc As PartDocument
    Dim attr As IXMLDOMAttribute
    Dim i As Integer
    Dim cur_rmin1 As String
    Dim cur_rmin2 As String
    Dim cur_rmax1 As String
    Dim cur_rmax2 As String
    Dim cur_dz As String
    Dim next_dz As Double
    Dim cur_shift As String

    'Is active document a part?
    If Right(CATIA.ActiveDocument.Name, 8) <> ".CATPart" Then
        MsgBox "The type of the active document must be a part", vbCritical, "Incorrect active document type"
        End
    End If
    Set prtDoc = CATIA.ActiveDocument
    
    Set attr = pconDOMDoc.createAttribute("startphi")
    attr.Value = txtSPhi.Text
    pconXMLNode.Attributes.setNamedItem attr

    Set attr = pconDOMDoc.createAttribute("deltaphi")
    attr.Value = txtDPhi.Text
    pconXMLNode.Attributes.setNamedItem attr

    If optHedra.Value = True Then
        Set attr = pconDOMDoc.createAttribute("numsides")
        attr.Value = txtNumSide.Text
        pconXMLNode.Attributes.setNamedItem attr
    End If

    txtXMLBefore.Text = pconDOMDoc.xml

    ' Print the section list into the file - prepare and open file
    Dim sFile As String, lFile As Long
    sFile = Environ("Temp") + "\poly.txt"
    lFile = FreeFile
    Open sFile For Append As lFile

    For i = 1 To pconXMLNode.childNodes.Length - 1
    
        cur_dz = Str((Val(pconXMLNode.childNodes.Item(i).Attributes.getNamedItem("z").nodeValue) - _
                    Val(pconXMLNode.childNodes.Item(i - 1).Attributes.getNamedItem("z").nodeValue)) / 2#)

        cur_rmin1 = pconXMLNode.childNodes.Item(i - 1).Attributes.getNamedItem("rmin").nodeValue
        cur_rmax1 = pconXMLNode.childNodes.Item(i - 1).Attributes.getNamedItem("rmax").nodeValue
        cur_rmin2 = pconXMLNode.childNodes.Item(i).Attributes.getNamedItem("rmin").nodeValue
        cur_rmax2 = pconXMLNode.childNodes.Item(i).Attributes.getNamedItem("rmax").nodeValue

        ' Print the section list into the file - print section
        Print #lFile, pconXMLNode.childNodes.Item(i - 1).Attributes.getNamedItem("z").nodeValue + vbTab + _
                        pconXMLNode.childNodes.Item(i - 1).Attributes.getNamedItem("rmin").nodeValue + vbTab + _
                        pconXMLNode.childNodes.Item(i - 1).Attributes.getNamedItem("rmax").nodeValue

        If i < pconXMLNode.childNodes.Length - 1 Then
            next_dz = (Val(pconXMLNode.childNodes.Item(i + 1).Attributes.getNamedItem("z").nodeValue) - _
                    Val(pconXMLNode.childNodes.Item(i).Attributes.getNamedItem("z").nodeValue)) / 2#
        End If

        If Val(cur_dz) = 0 Then
            GoTo Label
        End If

        If optHedra.Value = True Then
            CreateHedra txtElems.Text, prtDoc, cur_rmin1, cur_rmax1, cur_rmin2, cur_rmax2, cur_dz, _
                                pconXMLNode.Attributes.getNamedItem("startphi").nodeValue, _
                                pconXMLNode.Attributes.getNamedItem("deltaphi").nodeValue, _
                                pconXMLNode.Attributes.getNamedItem("numsides").nodeValue, "mm", "deg", True
        Else
            CreateCons txtElems.Text, prtDoc, cur_rmin1, cur_rmax1, cur_rmin2, cur_rmax2, cur_dz, _
                                pconXMLNode.Attributes.getNamedItem("startphi").nodeValue, _
                                pconXMLNode.Attributes.getNamedItem("deltaphi").nodeValue, "mm", "deg", True
        End If
    
        If i < pconXMLNode.childNodes.Length - 1 Then
            If next_dz = 0 Then
                cur_shift = Str(-(Val(pconXMLNode.childNodes.Item(i + 2).Attributes.getNamedItem("z").nodeValue) - _
                                Val(pconXMLNode.childNodes.Item(i - 1).Attributes.getNamedItem("z").nodeValue)) / 2#)
            Else
                cur_shift = Str(-(Val(pconXMLNode.childNodes.Item(i + 1).Attributes.getNamedItem("z").nodeValue) - _
                                Val(pconXMLNode.childNodes.Item(i - 1).Attributes.getNamedItem("z").nodeValue)) / 2#)
            End If
        Else
            cur_shift = Str((Val(pconXMLNode.childNodes.Item(i - 1).Attributes.getNamedItem("z").nodeValue) - _
                            Val(pconXMLNode.childNodes.Item(0).Attributes.getNamedItem("z").nodeValue)) / 2#)
        End If
        CreateShift prtDoc, "0", "0", cur_shift, "mm"

Label:
    Next i

    ' Print the section list into the file - last section
    Print #lFile, pconXMLNode.childNodes.Item(pconXMLNode.childNodes.Length - 1).Attributes.getNamedItem("z").nodeValue + vbTab + _
                    pconXMLNode.childNodes.Item(pconXMLNode.childNodes.Length - 1).Attributes.getNamedItem("rmin").nodeValue + vbTab + _
                    pconXMLNode.childNodes.Item(pconXMLNode.childNodes.Length - 1).Attributes.getNamedItem("rmax").nodeValue

    lblStatus.Caption = "Done."

    ' Print the section list into the file - close file
    Close lFile

End Sub

Private Sub cmbDel_Click()

    pconXMLNode.RemoveChild pconXMLNode.childNodes.Item(lstZplanes.ListIndex)
    lstZplanes.RemoveItem lstZplanes.ListIndex
    txtXMLBefore.Text = pconDOMDoc.xml

End Sub

Private Sub cmbExit_Click()

    End

End Sub

Private Sub cmbElems_Click()
'
'    cdcElems.Filter = "CATIA G4Primitives catalog (G4Primitives.catalog)|G4Primitives.catalog|All files (*.*)|*.*"
'    cdcElems.ShowOpen
'    If cdcElems.FileName = "" And txtElems.Text = "" Then
'        MsgBox "Invalid file name", vbCritical, "Error"
'        Exit Sub
'    ElseIf cdcElems.FileName = "" Then
'        Exit Sub
'    End If
'    txtElems.Text = Left(cdcElems.FileName, Len(cdcElems.FileName) - 20)
'
End Sub

Private Sub cmbUp_Click()

    If lstZplanes.ListIndex = 0 Then
        MsgBox "Moving up the first"
        Exit Sub
    End If

    Dim cur_min_node As IXMLDOMNode
    Dim i As Integer
    Dim selectedIndex As Integer
    
    selectedIndex = lstZplanes.ListIndex

    Set cur_min_node = pconXMLNode.childNodes.Item(selectedIndex)
    pconXMLNode.RemoveChild cur_min_node
    pconXMLNode.appendChild cur_min_node

    For i = selectedIndex To lstZplanes.ListCount - 1
        Set cur_min_node = pconXMLNode.childNodes.Item(selectedIndex - 1)
        pconXMLNode.RemoveChild cur_min_node
        pconXMLNode.appendChild cur_min_node
    Next i

    txtXMLBefore.Text = pconDOMDoc.xml
    PrintList

End Sub

Private Sub cmbDown_Click()

    If lstZplanes.ListIndex = lstZplanes.ListCount - 1 Then
        MsgBox "Moving down the last"
        Exit Sub
    End If

    Dim cur_min_node As IXMLDOMNode
    Dim i As Integer
    Dim selectedIndex As Integer
    
    selectedIndex = lstZplanes.ListIndex + 1

    Set cur_min_node = pconXMLNode.childNodes.Item(selectedIndex)
    pconXMLNode.RemoveChild cur_min_node
    pconXMLNode.appendChild cur_min_node

    For i = selectedIndex To lstZplanes.ListCount - 1
        Set cur_min_node = pconXMLNode.childNodes.Item(selectedIndex - 1)
        pconXMLNode.RemoveChild cur_min_node
        pconXMLNode.appendChild cur_min_node
    Next i

    txtXMLBefore.Text = pconDOMDoc.xml
    PrintList

End Sub

Private Sub lstZplanes_Change()

    If lstZplanes.ListIndex <> -1 Then
        cmbDel.Enabled = True
    Else
        cmbDel.Enabled = False
    End If

End Sub

Private Sub optCone_Change()

    If optCone.Value = True Then
        lblNumSide.Enabled = False
        txtNumSide.Enabled = False
    Else
        lblNumSide.Enabled = True
        txtNumSide.Enabled = True
    End If

End Sub

Private Sub UserForm_Click()

    txtXMLBefore.Text = pconDOMDoc.xml

End Sub

Private Sub UserForm_Initialize()

    Set pconDOMDoc = New DOMDocument60
    pconDOMDoc.appendChild pconDOMDoc.createElement("poly")
    Set pconXMLNode = pconDOMDoc.firstChild

    txtSPhi.Text = "0.0"
    txtDPhi.Text = "180.0"
    txtNumSide.Text = "7"
    txtElems.Text = CATIA.SystemService.Environ("BuilderPath") & "\02_Elements"

    txtZ.SetFocus

End Sub
