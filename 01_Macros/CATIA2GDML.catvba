Attribute VB_Name = "CATIA2GDML"
Option Explicit

Const STEPADD = 0.002

Global GDMLfile As New DOMDocument60

Dim defineElement As IXMLDOMElement
Dim materialsElement As IXMLDOMElement
Dim solidsElement As IXMLDOMElement
Dim structureElement As IXMLDOMElement
Dim setupElement As IXMLDOMElement

Sub CATMain()

    formCATIA2GDML.Show vbModeless

End Sub

Sub InitGDML(topVolumeName As String)

    ' Create the root "gdml" tag
    GDMLfile.appendChild GDMLfile.createElement("gdml")
    
    Dim GDMLrootElement As IXMLDOMElement
    Set GDMLrootElement = GDMLfile.firstChild
    
    Dim myProcInstruction As IXMLDOMProcessingInstruction
    Set myProcInstruction = GDMLfile.createProcessingInstruction("xml", "version='1.0' encoding='UTF-8'")
    GDMLfile.InsertBefore myProcInstruction, GDMLfile.firstChild
    
    Dim myAttr As IXMLDOMAttribute
    
    Support.createAttribute GDMLfile, GDMLrootElement, "xmlns:xsi", "http://www.w3.org/2001/XMLSchema-instance"
    Support.createAttribute GDMLfile, GDMLrootElement, "xsi:noNamespaceSchemaLocation", "http://service-spi.web.cern.ch/service-spi/app/releases/GDML/schema/gdml.xsd"
    
    ' Create empty "define", "materials", "solids" and "solids" section
    Set defineElement = GDMLrootElement.appendChild(GDMLfile.createElement("define"))
    Set materialsElement = GDMLrootElement.appendChild(GDMLfile.createElement("materials"))
    Set solidsElement = GDMLrootElement.appendChild(GDMLfile.createElement("solids"))
    Set structureElement = GDMLrootElement.appendChild(GDMLfile.createElement("structure"))
    
    ' Create and fill the "setup" section
    Set setupElement = GDMLrootElement.appendChild(GDMLfile.createElement("setup"))
    Support.createAttribute GDMLfile, setupElement, "name", "FAIRgeom"
    Support.createAttribute GDMLfile, setupElement, "version", "1.0"
    Dim worldTag As IXMLDOMElement
    Set worldTag = setupElement.appendChild(GDMLfile.createElement("world"))
    Support.createAttribute GDMLfile, worldTag, "ref", topVolumeName
    
End Sub

Sub PrepareDefineAndMaterialsSection(topProdDoc As ProductDocument)

    ' Independent variables "central", "identity" and DEGtoRAD --------------------------------------------------------
    Dim centralPositionElement As IXMLDOMElement
    Set centralPositionElement = defineElement.appendChild(GDMLfile.createElement("position"))
    Support.createAttribute GDMLfile, centralPositionElement, "name", "central"
    Support.createAttribute GDMLfile, centralPositionElement, "x", "0"
    Support.createAttribute GDMLfile, centralPositionElement, "y", "0"
    Support.createAttribute GDMLfile, centralPositionElement, "z", "0"
    Support.createAttribute GDMLfile, centralPositionElement, "unit", "mm"
               
    Dim identityRotationElement As IXMLDOMElement
    Set identityRotationElement = defineElement.appendChild(GDMLfile.createElement("rotation"))
    Support.createAttribute GDMLfile, identityRotationElement, "name", "identity"
    Support.createAttribute GDMLfile, identityRotationElement, "x", "0"
    Support.createAttribute GDMLfile, identityRotationElement, "y", "0"
    Support.createAttribute GDMLfile, identityRotationElement, "z", "0"
    Support.createAttribute GDMLfile, identityRotationElement, "unit", "degree"
    
    Dim degToRadElement As IXMLDOMElement
    Set degToRadElement = defineElement.appendChild(GDMLfile.createElement("variable"))
    Support.createAttribute GDMLfile, degToRadElement, "name", "DEGtoRAD"
    Support.createAttribute GDMLfile, degToRadElement, "value", Trim(Str(PI / 180#))

    ' User parameters and materials -----------------------------------------------------------------------------------
    
    Dim knownMaterials As New Collection
    
    Dim topProd As Product
    Dim prodParams As Parameters
    Set topProd = topProdDoc.Product
    Set prodParams = topProd.Parameters
    
    ' Loop over the parameters of the top product
    Dim iParam As Long
    For iParam = 1 To prodParams.Count

        ' Get the current parameter
        Dim curParam As Parameter
        Set curParam = prodParams.Item(iParam)
        
        ' Process only user parameters
        If (curParam.UserAccessMode = 2) Then
        
            ' Get parameter's value and corresponding relation
            Dim curParamRelation As Relation
            Dim curParamValue As String
            Set curParamRelation = curParam.OptionalRelation
            curParamValue = curParam.ValueAsString
                    
            ' Then parse the parameter name to split it
            Dim parsedParamName As Collection
            Set parsedParamName = Support.ParseParameterName(curParam.Name)

            ' Take the last token and check that it is not "Material"
            Dim lastName As String
            lastName = parsedParamName(parsedParamName.Count)
            If (lastName <> "Material" And lastName <> "material") Then
                'formCATIA2GDML.ListBox1.AddItem lastName + " = " + curParamValue
                
                Dim varElement As IXMLDOMElement
                Set varElement = defineElement.appendChild(GDMLfile.createElement("variable"))
                Support.createAttribute GDMLfile, varElement, "name", lastName

                If (curParamRelation Is Nothing) Then
                    Support.createAttribute GDMLfile, varElement, "value", Trim(curParamValue) ' Support.ValuePrepare(curParamValue) ???? needed?
                Else
                    Support.createAttribute GDMLfile, varElement, "value", ProcessFormula(RemoveUnits(curParamRelation.Value))
                End If
                
            Else ' Materials
            
                Dim materialName As String
                materialName = curParamValue
                
                If ((Not Support.Contains(knownMaterials, materialName)) And materialName <> "Assembly" And materialName <> "assembly") Then

                    knownMaterials.Add materialName

                    Dim curMaterialElement As IXMLDOMElement
                    Set curMaterialElement = materialsElement.appendChild(GDMLfile.createElement("material"))
                    Support.createAttribute GDMLfile, curMaterialElement, "name", materialName
                    Support.createAttribute GDMLfile, curMaterialElement, "Z", "1.0"
                    
                    Dim curMatChildElement As IXMLDOMElement
                    Set curMatChildElement = curMaterialElement.appendChild(GDMLfile.createElement("D"))
                    Support.createAttribute GDMLfile, curMatChildElement, "value", "1"
                    Set curMatChildElement = curMaterialElement.appendChild(GDMLfile.createElement("atom"))
                    Support.createAttribute GDMLfile, curMatChildElement, "value", "1"
                
                End If
                
            End If
        
        End If

    Next iParam ' End of loop over the parameters of the top product

End Sub

'Sub ParseCATIATree(topProdDoc As ProductDocument)
'
'    Dim topProd As Product
'    Dim prodParams As Parameters
'    Set topProd = topProdDoc.Product
'    Set prodParams = topProd.Parameters
'
'    ' Loop over the parameters of the top product
'    Dim iParam As Integer
'    For iParam = 1 To prodParams.Count
'
'        ' Get the current parameter
'        Dim curParam As Parameter
'        Set curParam = prodParams.Item(iParam)
'
'        Dim reconstructedName As String
'        reconstructedName = ProcessParameter(curParam)
'        formCATIA2GDML.ListBox1.AddItem reconstructedName
'
'    Next iParam
'
'End Sub

'Function ProcessParameter(curParam As Parameter) As String
'
'    ' Return object
'    Dim reconstructedName As String
'    reconstructedName = ""
'
'    ' Get parameter's value and corresponding relation
'    Dim curParamRelation As Relation
'    Dim curParamValue As String
'    Set curParamRelation = curParam.OptionalRelation
'    curParamValue = curParam.ValueAsString
'
'    ' Then parse the parameter name to split it and reconstruct the name back for checking
'    ' Print reconstructed name, value and formula into an output string
'    Dim parsedParamName As Collection
'    Set parsedParamName = Support.ParseParameterName(curParam.name)
'
'    Dim iSubStr As Integer
'    For iSubStr = 1 To parsedParamName.Count
'        Dim subStr As String
'        subStr = parsedParamName.Item(iSubStr)
'        reconstructedName = reconstructedName + subStr
'        If (iSubStr < parsedParamName.Count) Then reconstructedName = reconstructedName + " \ "
'    Next iSubStr
'
'    reconstructedName = reconstructedName + " = " + curParamValue
'
'    If Not (curParamRelation Is Nothing) Then
'        reconstructedName = reconstructedName + " = " + curParamRelation.Value
'    End If
'
'    ' Return statement
'    ProcessParameter = reconstructedName
'
'End Function


Public Sub LoopOverProduct(topProdDoc As ProductDocument)

    Dim topProd As Product
    Dim prods As Products
    Set topProd = topProdDoc.Product
    Set prods = topProd.Products
    
    ' Loop over the components of the top product
    Dim iProd As Integer
    For iProd = 1 To prods.Count
    
        formCATIA2GDML.Label2.Caption = "Processing part " + Trim(Str(iProd)) + " of " + Trim(Str(prods.Count))
    
        Dim prod As Product
        Dim prodInstanceName As String
        Dim prodPartNumber As String
        Dim prodFilename As String
        Dim prtDoc As PartDocument
        Dim prt As Part
        Dim prtProd As Product
        Dim prtParams As Parameters
        
        Set prod = prods.Item(iProd)
        prodInstanceName = prod.Name
        prodPartNumber = prod.PartNumber
        prodFilename = prod.ReferenceProduct.Parent.Name
        Set prtDoc = prod.ReferenceProduct.Parent
        Set prt = prtDoc.Part
        Set prtProd = prtDoc.Product
        Set prtParams = prt.Parameters
        
        formCATIA2GDML.ListBox1.AddItem "----------------------------------------------" + prodPartNumber + "----------------------------------------------"
        
        ' Loop over the parameters of the current component
'        Dim iParam As Integer
'        For iParam = 1 To prtParams.Count
'            Dim prtParam As Parameter
'            Set prtParam = prtParams.Item(iParam)
'
'            Dim reconstructedName As String
'            reconstructedName = ProcessParameter(prtParam)
'            formCATIA2GDML.ListBox1.AddItem reconstructedName
'        Next iParam
        
        Dim curVolumeTag As IXMLDOMElement
        Set curVolumeTag = Nothing
        
        ' Loop over the bodies
        Dim iBody As Integer
        For iBody = 1 To prt.Bodies.Count
            Dim curBody As Body
            Set curBody = prt.Bodies.Item(iBody)
            
            If (curBody.Name = "PartBody") Then
                ' Process the shape of the volume
                Call ProcessPartBody(curBody, prt)
                Set curVolumeTag = CreateLogicalVolume(prt, prtDoc)
            ElseIf (Left(curBody.Name, 5) = "Body.") Then
                ' Process the child volume
                Call ProcessPhysvolBody(curBody, prt, curVolumeTag)
            End If
            
        Next iBody
        
    Next iProd

End Sub

Private Function CreateLogicalVolume(prt As Part, prtDoc As PartDocument) As IXMLDOMElement

    Dim materialParam As Parameter
    Set materialParam = prt.Parameters.GetItem("Material")

    Dim volNode As IXMLDOMElement

    ' Material name defines whether it is a volume-assembly or (in any other case) just a standard volume
    If (materialParam.ValueAsString = "Assembly" Or materialParam.ValueAsString = "assembly") Then
        Set volNode = structureElement.appendChild(GDMLfile.createElement("assembly"))
        Support.createAttribute GDMLfile, volNode, "name", prt.Name
    Else
        Dim matRefNode As IXMLDOMElement
        Dim solidRefNode As IXMLDOMElement
        Set volNode = structureElement.appendChild(GDMLfile.createElement("volume"))
        Support.createAttribute GDMLfile, volNode, "name", prt.Name
        Set matRefNode = volNode.appendChild(GDMLfile.createElement("materialref"))
        Support.createAttribute GDMLfile, matRefNode, "ref", materialParam.ValueAsString
        Set solidRefNode = volNode.appendChild(GDMLfile.createElement("solidref"))
        Support.createAttribute GDMLfile, solidRefNode, "ref", prt.Name + "_PartBody"   ' We rely on naming here very much
    End If

''''' Color of the volume -----------------------------------------------------------------------------------------------------
''''' TODO implement in ROOT
'    Dim sel As Selection
'    Dim visPropSet As VisPropertySet
'    Dim colorR As Long, colorG As Long, colorB As Long
'
'    Set sel = prtDoc.Selection
'    sel.Clear
'    sel.Add prt.MainBody
'    Set visPropSet = sel.VisProperties
'    visPropSet.GetRealColor colorR, colorG, colorB
'    sel.Clear
'
'    formCATIA2GDML.ListBox1.AddItem "R=" + Trim(Str(colorR)) + " G=" + Trim(Str(colorG)) + " B=" + Trim(Str(colorB))
'
'    Dim auxNode As IXMLDOMElement
'    Set auxNode = volNode.appendChild(GDMLfile.createElement("auxiliary"))
'    Support.createAttribute GDMLfile, auxNode, "auxtype", "Color"
'    Support.createAttribute GDMLfile, auxNode, "auxvalue", Hex(colorR) + Hex(colorG) + Hex(colorB)
'
''''' -------------------------------------------------------------------------------------------------------------------------

    ' Return statement
    Set CreateLogicalVolume = volNode

End Function

' We rely too much on the names of the features and their amount
Sub ProcessPartBody(theBody As Body, prt As Part)

    formCATIA2GDML.ListBox1.AddItem "++++++++++++++++++++++++++++++++++++++++++++++++++++" + theBody.Name
    
    Dim iChild As Integer

'    ' Hybrid bodies
'    Dim hybBodies As HybridBodies
'    Set hybBodies = theBody.HybridBodies
'    formCATIA2GDML.ListBox1.AddItem "Hybrid bodies"
'    If Not (hybBodies Is Nothing) Then
'        For iChild = 1 To hybBodies.Count
'            formCATIA2GDML.ListBox1.AddItem hybBodies.Item(iChild).name
'        Next iChild
'    End If
'
'    ' Hybrid shapes
'    Dim hybShapes As HybridShapes
'    Set hybShapes = theBody.HybridShapes
'    formCATIA2GDML.ListBox1.AddItem "Hybrid shapes"
'    If Not (hybShapes Is Nothing) Then
'        For iChild = 1 To hybShapes.Count
'            formCATIA2GDML.ListBox1.AddItem hybShapes.Item(iChild).name
'        Next iChild
'    End If

    ' We can also use TypeName() to identify the type of the operation

    ' Shapes
    Dim shps As Shapes
    Set shps = theBody.Shapes
    If Not (shps Is Nothing) Then
        
        If (shps.Count = 1) Then
            ' Either a primitive shape (not Boolean) or an assembly-volume with one and only Add feature or ???
            
            Dim shp As Shape
            Set shp = shps.Item(1)
            
            If (Left(shp.Name, 2) = "G4") Then
                ' A primitive shape (not Boolean)
                'formCATIA2GDML.ListBox1.AddItem "" + shp.name
                
                Call Elements.ConstructPrimitive(theBody, prt, GDMLfile, solidsElement, prt.Name + "_PartBody")
                
            ElseIf (Left(shp.Name, 4) = "Add." Or Left(shp.Name, 14) = "Assembly_part.") Then
                ' An assembly-volume
                formCATIA2GDML.ListBox1.AddItem "*****************" + shp.Name
            
            Else
                ' ???
                
            End If
        
        ElseIf (shps.Count = 2) Then
            ' Only two shapes - either a Boolean operation or a volume-assembly with only two Add feature or ???

            Dim shp1 As Shape
            Dim shp2 As Shape
            Set shp1 = shps.Item(1)
            Set shp2 = shps.Item(2)
            
            If (Left(shp1.Name, 9) = "Assemble.") Then
                ' Boolean
                'formCATIA2GDML.ListBox1.AddItem "Boolean: " + shp1.name
                'formCATIA2GDML.ListBox1.AddItem "         " + shp2.name
                
                Dim levelCounter As Integer
                levelCounter = 0
                Call ProcessBoolean(theBody, prt, levelCounter, True)
                
            ElseIf (Left(shp1.Name, 4) = "Add." Or Left(shp1.Name, 14) = "Assembly_part.") Then
                ' Assembly-volume
                formCATIA2GDML.ListBox1.AddItem "*****************" + shp1.Name
                formCATIA2GDML.ListBox1.AddItem "*****************" + shp2.Name
            Else
                ' ???
            End If

        Else
            ' Multiple (more than 2) shapes - either a volume-assembly or ???
            For iChild = 1 To shps.Count
                formCATIA2GDML.ListBox1.AddItem "*****************" + shps.Item(iChild).Name
            Next iChild
            
        End If
    End If

End Sub

Function ProcessBoolean(theBody As Body, prt As Part, ByRef lvlCnt As Integer, Optional finalShape As Boolean = False) As String

    Dim shps As Shapes
    Set shps = theBody.Shapes

    Dim shp1 As Shape
    Dim shp2 As Shape

    If (shps.Count = 2) Then

        Set shp1 = shps.Item(1)
        Set shp2 = shps.Item(2)

        Dim operand1Body As Body
        Dim operand1BodyShapes As Shapes
        
        If (TypeName(shp1) = "Assemble") Then
        
            Dim shp1Assemble As Assemble
            Set shp1Assemble = shp1
            Set operand1Body = shp1Assemble.Body
            Set operand1BodyShapes = operand1Body.Shapes

            Dim operand2Body As Body

            Dim theBooleanNode As IXMLDOMElement

            ' Basically just identify the type here and fill operand2Body
            If (TypeName(shp2) = "Add") Then
                Dim shp2Add As Add
                Set shp2Add = shp2
                Set operand2Body = shp2Add.Body
            ElseIf (TypeName(shp2) = "Intersect") Then
                Dim shp2Intersect As Intersect
                Set shp2Intersect = shp2
                Set operand2Body = shp2Intersect.Body
            ElseIf (TypeName(shp2) = "Remove") Then
                Dim shp2Remove As Remove
                Set shp2Remove = shp2
                Set operand2Body = shp2Remove.Body
            Else
                ' error
                err.Raise vbObjectError + 513, "ProcessBoolean", "Second festure is not Add/Intersect/Remove."
            End If

            Dim operand2BodyShapes As Shapes
            Set operand2BodyShapes = operand2Body.Shapes
            
            ' -----------------------------------------------------------
            
            Dim firstOpName As String
            
            If (operand1BodyShapes.Count = 1) Then
                ' First operand is a primitive
                formCATIA2GDML.ListBox1.AddItem operand1BodyShapes.Item(1).Name + " - " + TypeName(operand1BodyShapes.Item(1)) + " - Level2 - " + Str(lvlCnt)
                firstOpName = Trim(Str(lvlCnt))
                Call Elements.ConstructPrimitive(operand1Body, prt, GDMLfile, solidsElement, prt.Name + "_PartBody_op" + firstOpName)
                lvlCnt = lvlCnt + 1
            ElseIf (operand1BodyShapes.Count = 2 And TypeName(operand1BodyShapes.Item(1)) = "Assemble") Then
                ' First operand is the Boolean operation
                firstOpName = ProcessBoolean(operand1Body, prt, lvlCnt)
            Else
                ' Actually this should never happen
                err.Raise vbObjectError + 513, "ProcessBoolean", "First operand is rotated/translated."
                ' It could be that here we have out UDF and at least one of the following: rotZ, rotY, rotX, trans. This is the second operand then!
            End If
            
            Dim secondOpName As String
            
            Dim positionAndRotation As New cls_PosRot
            Dim posXYZshift(2) As Double
            posXYZshift(0) = 0#
            posXYZshift(1) = 0#
            posXYZshift(2) = 0#
            
            If (operand2BodyShapes.Count = 1) Then
                ' Second operand is a primitive
                formCATIA2GDML.ListBox1.AddItem operand2BodyShapes.Item(1).Name + " - " + TypeName(operand2BodyShapes.Item(1)) + " - Level2 - " + Str(lvlCnt)
                secondOpName = Trim(Str(lvlCnt))
                Call Elements.ConstructPrimitive(operand2Body, prt, GDMLfile, solidsElement, prt.Name + "_PartBody_op" + secondOpName)
                lvlCnt = lvlCnt + 1
            ElseIf (operand2BodyShapes.Count = 2 And TypeName(operand2BodyShapes.Item(1)) = "Assemble") Then
                ' Second operand is the Boolean operation
                secondOpName = ProcessBoolean(operand2Body, prt, lvlCnt)
            Else
                ' It could be that here we have our UDF and at least one of the following: rotX, rotY, rotZ, trans. This is the second operand then!
                If (TypeName(operand2BodyShapes.Item(1)) = "ShapeInstance") Then
                    formCATIA2GDML.ListBox1.AddItem operand2BodyShapes.Item(1).Name + " - " + TypeName(operand2BodyShapes.Item(1)) + " - Level2 - " + Str(lvlCnt)
                    secondOpName = Trim(Str(lvlCnt))
                    Call Elements.ConstructPrimitive(operand2Body, prt, GDMLfile, solidsElement, prt.Name + "_PartBody_op" + secondOpName)
                    lvlCnt = lvlCnt + 1
                    
                    ' Loop over the features inside the body - rotations and translation
                    Dim j As Integer
                    For j = 2 To operand2BodyShapes.Count
                        
                        If ((LCase(Left(operand2BodyShapes.Item(j).Name, 8)) = "rotate.z") Or _
                        (LCase(Left(operand2BodyShapes.Item(j).Name, 8)) = "rotate.y") Or _
                        (LCase(Left(operand2BodyShapes.Item(j).Name, 8)) = "rotate.x")) Then
                        
                            Dim rotateFeature As Rotate
                            Set rotateFeature = operand2BodyShapes.Item(j)
                            Call positionAndRotation.ProcessRotateFeature(rotateFeature)                        ' MAIN CALL HERE
                        
                        ElseIf (LCase(Left(operand2BodyShapes.Item(j).Name, 10)) = "translate.") Then
                            Dim transFeature As HybridShape
                            Set transFeature = operand2BodyShapes.Item(j)
                            Call positionAndRotation.ProcessTranslateFeature(transFeature, prt)                 ' MAIN CALL HERE

                        Else
                        End If
                        
                    Next j ' end of loop over rotations and translation
                    
                End If
            End If

            ' -----------------------------------------------------------
            
            formCATIA2GDML.ListBox1.AddItem "Boolean: " + shp1.Name + " - " + TypeName(shp1)
            formCATIA2GDML.ListBox1.AddItem "         " + shp2.Name + " - " + TypeName(shp2)
            
            If (TypeName(shp2) = "Add") Then
                Set theBooleanNode = solidsElement.appendChild(GDMLfile.createElement("union"))
            ElseIf (TypeName(shp2) = "Intersect") Then
                Set theBooleanNode = solidsElement.appendChild(GDMLfile.createElement("intersection"))
            ElseIf (TypeName(shp2) = "Remove") Then
                Set theBooleanNode = solidsElement.appendChild(GDMLfile.createElement("subtraction"))
            Else
                ' error
                err.Raise vbObjectError + 513, "ProcessBoolean", "Second feature is not Add/Intersect/Remove."
            End If

            Dim booleanResultName As String
            ProcessBoolean = firstOpName + secondOpName
            
            If (finalShape) Then
                booleanResultName = prt.Name + "_PartBody"
            Else
                booleanResultName = prt.Name + "_PartBody_op" + firstOpName + secondOpName
            End If
            
            Dim firstNode As IXMLDOMElement
            Dim secondNode As IXMLDOMElement
            Dim posNode As IXMLDOMElement
            Dim rotNode As IXMLDOMElement
            
            ' Create the boolean operation tag in the GDML file
            Support.createAttribute GDMLfile, theBooleanNode, "name", booleanResultName
            ' Set the first and the second operands
            Set firstNode = theBooleanNode.appendChild(GDMLfile.createElement("first"))
            Set secondNode = theBooleanNode.appendChild(GDMLfile.createElement("second"))
            Support.createAttribute GDMLfile, firstNode, "ref", prt.Name + "_PartBody_op" + firstOpName
            Support.createAttribute GDMLfile, secondNode, "ref", prt.Name + "_PartBody_op" + secondOpName
            
            ' Set the rotations and the traslation
            'TODO implement relations for the translation. Done? Check!
            'TODO implement names for the rotation and translation tags. Done? Check!
            Call GeneratePosition(theBooleanNode, posXYZshift, positionAndRotation, secondOpName, firstOpName, False, prt.Name + "_PartBody__") ' MAIN CALL HERE

        Else
            ' error
            err.Raise vbObjectError + 513, "ProcessBoolean", "The first feature is not Assemble."
        End If
        
    ElseIf (shps.Count = 1) Then
        ' error
        Set shp1 = shps.Item(1)
        formCATIA2GDML.ListBox1.AddItem shp1.Name + " - " + TypeName(shp1) + " - Level1"
        
        err.Raise vbObjectError + 513, "ProcessBoolean", "Only one feature, two expected."
    Else
        ' error
        err.Raise vbObjectError + 513, "ProcessBoolean", "More than two features, two expected."
    End If

End Function

Sub ProcessPhysvolBody(theBody As Body, prt As Part, volTag As IXMLDOMElement)

    formCATIA2GDML.ListBox1.AddItem "====================" + theBody.Name
    
    Dim sol As Solid
    Dim srcProd As Product
    Set sol = theBody.Shapes.Item(1)
    Set srcProd = sol.SourceProduct
    
    Dim motherVolName As String
    Dim childVolName As String
    motherVolName = prt.Name
    childVolName = srcProd.PartNumber

    Dim suffix As String
    Dim suffixStartPos As Long
    suffixStartPos = InStr(1, theBody.Name, childVolName, vbTextCompare) + Len(childVolName) + 1
    suffix = Mid(theBody.Name, suffixStartPos)

    Dim suffix2 As String

    'TODO Check the order of transformation here in the CATIA tree!
    If (LCase(Left(theBody.Shapes.Item(2).Name, 8)) <> "rotate.z" Or _
        LCase(Left(theBody.Shapes.Item(3).Name, 8)) <> "rotate.y" Or _
        LCase(Left(theBody.Shapes.Item(4).Name, 8)) <> "rotate.x" Or _
        LCase(Left(theBody.Shapes.Item(5).Name, 10)) <> "translate.") Then
        'error
        err.Raise vbObjectError + 513, "ProcessPhysvolBody", "Wrong order of transformation features. Must be rotation around Z, Y, X, and then translation."
    End If
    'TODO test this
    
    
    Dim positionAndRotation As New cls_PosRot

    Dim posXYZshift(2) As Double ' This is required for array
    posXYZshift(0) = 0#
    posXYZshift(1) = 0#
    posXYZshift(2) = 0#
    
    ' Related to the pattern - array or replica
    Dim doArray As Boolean
    Dim doReplica As Boolean
    doArray = False
    doReplica = False
    Dim pattDir As String
    Dim nDir1 As Integer
    Dim nDir2 As Integer
    Dim stepDir1 As Double
    Dim stepDir2 As Double

    ' nDir1, nDir2, stepDir1, stepDir2
    Dim patternWithRelation(3) As Boolean
    patternWithRelation(0) = False
    patternWithRelation(1) = False
    patternWithRelation(2) = False
    patternWithRelation(3) = False
    Dim patternRelation(3) As String
    
    'TODO implement different checks
    If (theBody.Shapes.Count < 5) Then
        'error
        err.Raise vbObjectError + 513, "ProcessPhysvolBody", "Wrong number of features in the body representing a physical volume."
    End If
    'TODO test this
    
    Dim iShape As Integer
    For iShape = 2 To theBody.Shapes.Count
        'formCATIA2GDML.ListBox1.AddItem theBody.Shapes.Item(iShape).name

        If ((LCase(Left(theBody.Shapes.Item(iShape).Name, 8)) = "rotate.z") Or _
            (LCase(Left(theBody.Shapes.Item(iShape).Name, 8)) = "rotate.y") Or _
            (LCase(Left(theBody.Shapes.Item(iShape).Name, 8)) = "rotate.x")) Then
            
            Dim rotateFeature As Rotate
            Set rotateFeature = theBody.Shapes.Item(iShape)
            Call positionAndRotation.ProcessRotateFeature(rotateFeature)                        ' MAIN CALL HERE

        ElseIf (LCase(Left(theBody.Shapes.Item(iShape).Name, 10)) = "translate.") Then
            Dim transFeature As HybridShape
            Set transFeature = theBody.Shapes.Item(iShape)
            Call positionAndRotation.ProcessTranslateFeature(transFeature, prt)                 ' MAIN CALL HERE

        ' Array and replica
        'TODO implement circular array and replica
        ElseIf (LCase(Left(theBody.Shapes.Item(iShape).Name, 6)) = "array." Or _
                LCase(Left(theBody.Shapes.Item(iShape).Name, 8)) = "replica.") Then

            If (LCase(Left(theBody.Shapes.Item(iShape).Name, 6)) = "array.") Then
                doArray = True
            Else
                doReplica = True
            End If

            Dim patternFeature As Pattern
            Set patternFeature = theBody.Shapes.Item(iShape)
            Call ProcessPattern(patternFeature, prt, patternWithRelation, patternRelation, pattDir, nDir1, nDir2, stepDir1, stepDir2)  ' MAIN CALL HERE

        Else
            'error
        End If
        
    Next iShape

    Dim physVolTag As IXMLDOMElement
    Dim divisionVolTag As IXMLDOMElement
    Dim volRefTag As IXMLDOMElement
    
    If (doReplica) Then     ' Replica
    
        'TODO Additional checks
        If (nDir2 > 1) Then
            ' error
        End If
    
        'TODO implement GEANT4 case
        Set divisionVolTag = volTag.appendChild(GDMLfile.createElement("divisionvol"))
        
        If (patternWithRelation(0)) Then
            Call Support.createAttribute(GDMLfile, divisionVolTag, "number", patternRelation(0))
        Else
            Call Support.createAttribute(GDMLfile, divisionVolTag, "number", Trim(Str(nDir1)))
        End If
        If (patternWithRelation(2)) Then
            Call Support.createAttribute(GDMLfile, divisionVolTag, "width", ProcessFormula(RemoveUnits(patternRelation(2))) + "-" + Trim(Str(STEPADD)))
        Else
            Call Support.createAttribute(GDMLfile, divisionVolTag, "width", RemoveUnits(Trim(Str(stepDir1 - STEPADD))))
        End If
        
        Call Support.createAttribute(GDMLfile, divisionVolTag, "offset", "0")
        Select Case pattDir
        Case "x":
            Call Support.createAttribute(GDMLfile, divisionVolTag, "axis", "kXAxis")
        Case "y":
            Call Support.createAttribute(GDMLfile, divisionVolTag, "axis", "kYAxis")
        Case "z":
            Call Support.createAttribute(GDMLfile, divisionVolTag, "axis", "kZAxis")
        Case "p":
            'TODO implement
        End Select
        Call Support.createAttribute(GDMLfile, divisionVolTag, "unit", "mm")
        Set volRefTag = divisionVolTag.appendChild(GDMLfile.createElement("volumeref"))
        Call Support.createAttribute(GDMLfile, volRefTag, "ref", childVolName)
    
    Else                    ' Physical volume or array

        Set physVolTag = volTag.appendChild(GDMLfile.createElement("physvol"))
        
        '17.09.2018 - patch required for ROOT6
        Call Support.createAttribute(GDMLfile, physVolTag, "copynumber", suffix) 'TODO
        
        Set volRefTag = physVolTag.appendChild(GDMLfile.createElement("volumeref"))
        Call Support.createAttribute(GDMLfile, volRefTag, "ref", childVolName)
    
        ' Apply positioning of the only physvol (of the first for the case of array)
        Call GeneratePosition(physVolTag, posXYZshift, positionAndRotation, childVolName, motherVolName)     ' MAIN CALL HERE
    
        ' If there is an array - create remaining physvolumes
        Dim iInstance As Integer
        If (doArray) Then
            Select Case pattDir
            Case "x":
                For iInstance = 1 To nDir1 - 1
                    Set physVolTag = volTag.appendChild(GDMLfile.createElement("physvol"))
                    suffix2 = Trim(Str(val(suffix) + iInstance))
                    Call Support.createAttribute(GDMLfile, physVolTag, "copynumber", suffix2)
                    Set volRefTag = physVolTag.appendChild(GDMLfile.createElement("volumeref"))
                    Call Support.createAttribute(GDMLfile, volRefTag, "ref", childVolName)
                    posXYZshift(0) = iInstance * stepDir1
                    Call GeneratePosition(physVolTag, posXYZshift, positionAndRotation, childVolName, motherVolName) ' MAIN CALL HERE
                Next iInstance
            
            Case "y":
                For iInstance = 1 To nDir1 - 1
                    Set physVolTag = volTag.appendChild(GDMLfile.createElement("physvol"))
                    suffix2 = Trim(Str(val(suffix) + iInstance))
                    Call Support.createAttribute(GDMLfile, physVolTag, "copynumber", suffix2)
                    Set volRefTag = physVolTag.appendChild(GDMLfile.createElement("volumeref"))
                    Call Support.createAttribute(GDMLfile, volRefTag, "ref", childVolName)
                    posXYZshift(1) = iInstance * stepDir1
                    Call GeneratePosition(physVolTag, posXYZshift, positionAndRotation, childVolName, motherVolName) ' MAIN CALL HERE
                Next iInstance
            
            Case "z":
                For iInstance = 1 To nDir1 - 1
                    Set physVolTag = volTag.appendChild(GDMLfile.createElement("physvol"))
                    suffix2 = Trim(Str(val(suffix) + iInstance))
                    Call Support.createAttribute(GDMLfile, physVolTag, "copynumber", suffix2)
                    Set volRefTag = physVolTag.appendChild(GDMLfile.createElement("volumeref"))
                    Call Support.createAttribute(GDMLfile, volRefTag, "ref", childVolName)
                    posXYZshift(2) = iInstance * stepDir1
                    Call GeneratePosition(physVolTag, posXYZshift, positionAndRotation, childVolName, motherVolName) ' MAIN CALL HERE
                Next iInstance
            
            Case "rotx":
                'TODO implement
            Case "roty":
                'TODO implement
            Case "rotz":
                'TODO implement
                
            Case "xy":
                'TODO implement
            Case "yz":
                'TODO implement
            Case "zx":
                'TODO implement
            End Select
            
        End If
    
    End If

End Sub
                            
Private Sub GeneratePosition(physVolTag As IXMLDOMElement, posXYZshift() As Double, _
                             positionAndRotation As cls_PosRot, _
                             childVolName As String, motherVolName As String, _
                             Optional invertAngles As Boolean = True, Optional prefix As String = "")

    ' Position
    Dim posNode As IXMLDOMElement
    If (positionAndRotation.posXYZwithRelation(0) = False And _
        positionAndRotation.posXYZwithRelation(1) = False And _
        positionAndRotation.posXYZwithRelation(2) = False And _
        positionAndRotation.posXYZcoord(0) + posXYZshift(0) = 0# And _
        positionAndRotation.posXYZcoord(1) + posXYZshift(1) = 0# And _
        positionAndRotation.posXYZcoord(2) + posXYZshift(2) = 0#) Then
        ' If there is no translation - create reference to the zero-translation
        Set posNode = physVolTag.appendChild(GDMLfile.createElement("positionref"))
        Support.createAttribute GDMLfile, posNode, "ref", "central"
    Else
        Set posNode = physVolTag.appendChild(GDMLfile.createElement("position"))
        Support.createAttribute GDMLfile, posNode, "name", prefix + childVolName + "_pos_" + motherVolName

        ' Create the position tag attribute either with the formula or with the value
        If (positionAndRotation.posXYZwithRelation(0) = False) Then
            Support.createAttribute GDMLfile, posNode, "x", Trim(Str(positionAndRotation.posXYZcoord(0) + posXYZshift(0)))
        Else
            If (posXYZshift(0) <> 0#) Then
                Support.createAttribute GDMLfile, posNode, "x", ProcessFormula(RemoveUnits(positionAndRotation.posXYZformula(0))) + "+" + Trim(Str(posXYZshift(0)))
            Else
                Support.createAttribute GDMLfile, posNode, "x", ProcessFormula(RemoveUnits(positionAndRotation.posXYZformula(0)))
            End If
        End If
        If (positionAndRotation.posXYZwithRelation(1) = False) Then
            Support.createAttribute GDMLfile, posNode, "y", Trim(Str(positionAndRotation.posXYZcoord(1) + posXYZshift(1)))
        Else
            If (posXYZshift(1) <> 0#) Then
                Support.createAttribute GDMLfile, posNode, "y", ProcessFormula(RemoveUnits(positionAndRotation.posXYZformula(1))) + "+" + Trim(Str(posXYZshift(1)))
            Else
                Support.createAttribute GDMLfile, posNode, "y", ProcessFormula(RemoveUnits(positionAndRotation.posXYZformula(1)))
            End If
        End If
        If (positionAndRotation.posXYZwithRelation(2) = False) Then
            Support.createAttribute GDMLfile, posNode, "z", Trim(Str(positionAndRotation.posXYZcoord(2) + posXYZshift(2)))
        Else
            If (posXYZshift(2) <> 0#) Then
                Support.createAttribute GDMLfile, posNode, "z", ProcessFormula(RemoveUnits(positionAndRotation.posXYZformula(2))) + "+" + Trim(Str(posXYZshift(2)))
            Else
                Support.createAttribute GDMLfile, posNode, "z", ProcessFormula(RemoveUnits(positionAndRotation.posXYZformula(2)))
            End If
        End If

        Support.createAttribute GDMLfile, posNode, "unit", "mm"
    End If
    
    ' Rotation
    Dim rotNode As IXMLDOMElement
    If (positionAndRotation.rotZYXwithRelation(0) = False And _
        positionAndRotation.rotZYXwithRelation(1) = False And _
        positionAndRotation.rotZYXwithRelation(2) = False And _
        positionAndRotation.rotZYXangle(0) = 0# And _
        positionAndRotation.rotZYXangle(1) = 0# And _
        positionAndRotation.rotZYXangle(2) = 0#) Then
        ' If there is no rotation - create reference to the zero-rotation
        Set rotNode = physVolTag.appendChild(GDMLfile.createElement("rotationref"))
        Support.createAttribute GDMLfile, rotNode, "ref", "identity"
    Else
        Set rotNode = physVolTag.appendChild(GDMLfile.createElement("rotation"))
        Support.createAttribute GDMLfile, rotNode, "name", prefix + childVolName + "_rot_" + motherVolName
        
        ' Create the rotation tag attribute either with the formula or with the value
        Dim valueToWrite As String

        ' We write into GDML in the order X Y Z
        ' However in the array the order is Z Y X
        ' GDML does not care how it is written

        If (positionAndRotation.rotZYXwithRelation(2) = False) Then
            valueToWrite = Trim(Str(positionAndRotation.rotZYXangle(2)))
        Else
            valueToWrite = ProcessFormula(RemoveUnits(positionAndRotation.rotZYXformula(2)))
        End If
        If (invertAngles) Then valueToWrite = "-(" + valueToWrite + ")"                         ' INVERT ANGLES if specified
        Support.createAttribute GDMLfile, rotNode, "x", valueToWrite
        
        If (positionAndRotation.rotZYXwithRelation(1) = False) Then
            valueToWrite = Trim(Str(positionAndRotation.rotZYXangle(1)))
        Else
            valueToWrite = ProcessFormula(RemoveUnits(positionAndRotation.rotZYXformula(1)))
        End If
        If (invertAngles) Then valueToWrite = "-(" + valueToWrite + ")"                         ' INVERT ANGLES if specified
        Support.createAttribute GDMLfile, rotNode, "y", valueToWrite
        
        If (positionAndRotation.rotZYXwithRelation(0) = False) Then
            valueToWrite = Trim(Str(positionAndRotation.rotZYXangle(0)))
        Else
            valueToWrite = ProcessFormula(RemoveUnits(positionAndRotation.rotZYXformula(0)))
        End If
        If (invertAngles) Then valueToWrite = "-(" + valueToWrite + ")"                         ' INVERT ANGLES if specified
        Support.createAttribute GDMLfile, rotNode, "z", valueToWrite

        Support.createAttribute GDMLfile, rotNode, "unit", "deg"
    End If

End Sub

Private Sub ProcessPattern(patternFeature As Pattern, prt As Part, patternWithRelation() As Boolean, patternRelation() As String, _
                                pattDir As String, nDir1 As Integer, nDir2 As Integer, stepDir1 As Double, stepDir2 As Double)

If (TypeName(patternFeature) = "CircPattern") Then
    'Err.Raise vbObjectError + 513, "ProcessPattern", "Unsupported array direction."
    MsgBox "Unsupported array direction. Skipping."
    Exit Sub
End If

    ' Determine and store the pattern parameters
    Dim patternParams As Parameters
    Set patternParams = prt.Parameters.SubList(patternFeature, True)
    Dim iParam As Integer
    For iParam = 1 To patternParams.Count
        ' Number of instances in the direction 1
        If (InStr(1, patternParams.Item(iParam).Name, patternFeature.FirstDirectionRepartition.InstancesCount.Name)) Then
            nDir1 = patternFeature.FirstDirectionRepartition.InstancesCount.Value
            If (patternParams.Item(iParam).OptionalRelation Is Nothing) Then
                formCATIA2GDML.ListBox1.AddItem patternParams.Item(iParam).Name + " val=" + Trim(Str(nDir1))
            Else
                patternWithRelation(0) = True
                patternRelation(0) = patternParams.Item(iParam).OptionalRelation.Value
                formCATIA2GDML.ListBox1.AddItem patternParams.Item(iParam).Name + " val=" + Trim(Str(nDir1)) + " relation=" + patternRelation(0)
            End If
        ' Number of instances in the direction 2
        ElseIf (InStr(1, patternParams.Item(iParam).Name, patternFeature.SecondDirectionRepartition.InstancesCount.Name)) Then
            nDir2 = patternFeature.SecondDirectionRepartition.InstancesCount.Value
            If (patternParams.Item(iParam).OptionalRelation Is Nothing) Then
                formCATIA2GDML.ListBox1.AddItem patternParams.Item(iParam).Name + " val=" + Trim(Str(nDir2))
            Else
                patternWithRelation(1) = True
                patternRelation(1) = patternParams.Item(iParam).OptionalRelation.Value
                formCATIA2GDML.ListBox1.AddItem patternParams.Item(iParam).Name + " val=" + Trim(Str(nDir2)) + " relation=" + patternRelation(1)
            End If
        ' Spacing in the direction 1
        ElseIf (InStr(1, patternParams.Item(iParam).Name, patternFeature.FirstDirectionRepartition.Spacing.Name)) Then
            stepDir1 = patternFeature.FirstDirectionRepartition.Spacing.Value
            If (patternParams.Item(iParam).OptionalRelation Is Nothing) Then
                formCATIA2GDML.ListBox1.AddItem patternParams.Item(iParam).Name + " val=" + Trim(Str(stepDir1))
            Else
                patternWithRelation(2) = True
                patternRelation(2) = patternParams.Item(iParam).OptionalRelation.Value
                formCATIA2GDML.ListBox1.AddItem patternParams.Item(iParam).Name + " val=" + Trim(Str(stepDir1)) + " relation=" + patternRelation(2)
            End If
        ' Spacing in the direction 2
        ElseIf (InStr(1, patternParams.Item(iParam).Name, patternFeature.SecondDirectionRepartition.Spacing.Name)) Then
            stepDir2 = patternFeature.SecondDirectionRepartition.Spacing.Value
            If (patternParams.Item(iParam).OptionalRelation Is Nothing) Then
                formCATIA2GDML.ListBox1.AddItem patternParams.Item(iParam).Name + " val=" + Trim(Str(stepDir2))
            Else
                patternWithRelation(3) = True
                patternRelation(3) = patternParams.Item(iParam).OptionalRelation.Value
                formCATIA2GDML.ListBox1.AddItem patternParams.Item(iParam).Name + " val=" + Trim(Str(stepDir2)) + " relation=" + patternRelation(3)
            End If
        Else
            ' ???
        End If
    Next iParam

    'TODO implement circular array/replia
    ' Order of cases matters here!
    If (LCase(Left(patternFeature.Name, 8)) = "array.xy") Then
        pattDir = "xy"
    ElseIf (LCase(Left(patternFeature.Name, 8)) = "array.yz") Then
        pattDir = "yz"
    ElseIf (LCase(Left(patternFeature.Name, 8)) = "array.zx") Then
        pattDir = "zx"
    ElseIf (LCase(Left(patternFeature.Name, 7)) = "array.x" Or LCase(Left(patternFeature.Name, 9)) = "replica.x") Then
        pattDir = "x"
    ElseIf (LCase(Left(patternFeature.Name, 7)) = "array.y" Or LCase(Left(patternFeature.Name, 9)) = "replica.y") Then
        pattDir = "y"
    ElseIf (LCase(Left(patternFeature.Name, 7)) = "array.z" Or LCase(Left(patternFeature.Name, 9)) = "replica.z") Then
        pattDir = "z"
    Else
        ' error
        err.Raise vbObjectError + 513, "ProcessPattern", "Unrecognized pattern direction."
    End If

End Sub

' Make nice line endgins
Public Sub Postprocess(infilename As String, outfilename As String)

    Open infilename For Input As #1
    Open outfilename For Output As #2

    Dim readLine As String
    Dim fixedLine As String
    
    Do Until EOF(1)
        Line Input #1, readLine
        
        fixedLine = Replace(readLine, "><", ">" + vbNewLine + "<")
        
        Print #2, fixedLine
    Loop

    Close #1
    Close #2

End Sub

Attribute VB_Name = "DialogsVB7"
Option Explicit

'----------------------------------------------------------------------

' 64 bit VBA 7 version of File and Folder Browswers

' FileBrowseOpen()
' FileBrowseSave()
' FolderBrowse()

' Much of the original 32 bit module was donated by the good people of XtremeVbTalk.com
' I massaged it to be 64 bit with VBA 7 code lifted from numerous sites on the web

'----------------------------------------------------------------------

#If VBA7 Then

Private Declare PtrSafe Function GetOpenFileName Lib "comdlg32.dll" Alias _
    "GetOpenFileNameA" (pOpenfilename As OPENFILENAME) As Long

Private Declare PtrSafe Function GetSaveFileName Lib "comdlg32.dll" Alias _
    "GetSaveFileNameA" (pOpenfilename As OPENFILENAME) As Long

Private Declare PtrSafe Function SHBrowseForFolder Lib "shell32.dll" Alias _
    "SHBrowseForFolderA" (lpBrowseInfo As BrowseInfo) As Long

Private Declare PtrSafe Function SHGetPathFromIDList Lib "shell32.dll" _
    (ByVal pidList As LongPtr, ByVal lpBuffer As String) As Long

Public Declare PtrSafe Function SendMessageA Lib "user32" _
    (ByVal Hwnd As LongPtr, ByVal wMsg As Long, _
    ByVal wParam As LongPtr, lParam As Any) As LongPtr

Private Declare PtrSafe Sub CoTaskMemFree Lib "ole32.dll" (ByVal hMem As LongPtr)

Private Const BIF_RETURNONLYFSDIRS As Long = 1
Private Const CSIDL_DRIVES As Long = &H11
Private Const WM_USER As Long = &H400
Private Const MAX_PATH As Long = 260

'// message from browser
Private Const BFFM_INITIALIZED As Long = 1
Private Const BFFM_SELCHANGED As Long = 2
Private Const BFFM_VALIDATEFAILEDA As Long = 3 '// lParam:szPath ret:1(cont),0(EndDialog)
Private Const BFFM_VALIDATEFAILEDW As Long = 4 '// lParam:wzPath ret:1(cont),0(EndDialog)
Private Const BFFM_IUNKNOWN As Long = 5 '// provides IUnknown to client. lParam: IUnknown*

'// messages to browser
Private Const BFFM_SETSTATUSTEXTA As Long = WM_USER + 100
Private Const BFFM_ENABLEOK As Long = WM_USER + 101
Private Const BFFM_SETSELECTIONA As Long = WM_USER + 102
Private Const BFFM_SETSELECTIONW As Long = WM_USER + 103
Private Const BFFM_SETSTATUSTEXTW As Long = WM_USER + 104
Private Const BFFM_SETOKTEXT As Long = WM_USER + 105 '// Unicode only
Private Const BFFM_SETEXPANDED As Long = WM_USER + 106 '// Unicode only

Private Type OPENFILENAME
    lStructSize As Long
    hWndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As LongPtr
    lpTemplateName As String
End Type

Public Type BrowseInfo
    hWndOwner As LongPtr
    pIDLRoot As LongPtr
    pszDisplayName As String
    lpszTitle As String
    ulFlags As Long
    lpfnCallback As LongPtr
    lParam As LongPtr
    iImage As Long
End Type

'====== File Browsers for 64 bit VBA 7 ========

Public Function FileBrowseOpen(ByVal sInitFolder As String, _
    ByVal sTitle As String, _
    ByVal sFilter As String, _
    ByVal nFilterIndex As Integer) As String

    Dim OpenFile As OPENFILENAME
    Dim lReturn As Long
    
    sInitFolder = CorrectPath(sInitFolder)
    
    OpenFile.lpstrInitialDir = sInitFolder
    
    ' Swap filter separator for api separator
    sFilter = Replace(sFilter, "|", Chr(0))
    
    OpenFile.lpstrFilter = sFilter
    OpenFile.nFilterIndex = nFilterIndex
    OpenFile.lpstrTitle = sTitle
    
    
    OpenFile.hWndOwner = 0
    OpenFile.lpstrFile = String(257, 0)
    
    OpenFile.nMaxFile = LenB(OpenFile.lpstrFile) - 1
    OpenFile.lStructSize = LenB(OpenFile)
    
    OpenFile.lpstrFileTitle = OpenFile.lpstrFile
    OpenFile.nMaxFileTitle = OpenFile.nMaxFile
    
    OpenFile.flags = 0
    
    lReturn = GetOpenFileName(OpenFile)
    
    If lReturn = 0 Then
    FileBrowseOpen = ""
    Else
    FileBrowseOpen = Trim(Left(OpenFile.lpstrFile, InStr(1, OpenFile.lpstrFile, vbNullChar) - 1))
    End If

End Function

Public Function FileBrowseSave(ByVal sDefaultFilename As String, _
    ByVal sInitFolder As String, _
    ByVal sTitle As String, _
    ByVal sFilter As String, _
    ByVal nFilterIndex As Integer) As String

    Dim PadCount As Integer
    Dim OpenFile As OPENFILENAME
    Dim lReturn As Long
    
    sInitFolder = CorrectPath(sInitFolder)
    
    ' Swap filter separator for api separator
    sFilter = Replace(sFilter, "|", Chr(0))
    
    OpenFile.lpstrFilter = sFilter
    OpenFile.nFilterIndex = 1
    OpenFile.hWndOwner = 0
    
    PadCount = 260 - Len(sDefaultFilename)
    OpenFile.lpstrFile = sDefaultFilename & String(PadCount, Chr(0))
    'OpenFile.lpstrFile = String(257, 0)
    
    OpenFile.nMaxFile = LenB(OpenFile.lpstrFile) - 1
    OpenFile.lStructSize = LenB(OpenFile)
    
    OpenFile.lpstrFileTitle = OpenFile.lpstrFile
    OpenFile.nMaxFileTitle = OpenFile.nMaxFile
    OpenFile.lpstrInitialDir = sInitFolder
    OpenFile.lpstrTitle = sTitle
    OpenFile.flags = 0
    lReturn = GetSaveFileName(OpenFile)
    
    If lReturn = 0 Then
    FileBrowseSave = ""
    Else
    FileBrowseSave = Trim(Left(OpenFile.lpstrFile, InStr(1, OpenFile.lpstrFile, vbNullChar) - 1))
    End If

End Function

'====== Folder Browser for 64 bit VBA 7 ========

Public Function FolderBrowse(ByVal sDialogTitle As String, ByVal sInitFolder As String) As String

    Dim ReturnPath As String
    
    Dim b(MAX_PATH) As Byte
    Dim pItem As Long
    Dim sFullPath As String
    Dim bi As BrowseInfo
    Dim ppidl As Long
    
    sInitFolder = CorrectPath(sInitFolder)
    
    ' Note VBA windows and dialogs do not have an hWnd property.
    bi.hWndOwner = 0 'Windows Main Screen handle.
    
    ' SHGetSpecialFolderLocation bi.hWndOwner, CSIDL_DRIVES, ppidl
    
    bi.pIDLRoot = 0 'ppidl
    
    bi.pszDisplayName = VarPtr(b(0))
    bi.lpszTitle = sDialogTitle
    bi.ulFlags = BIF_RETURNONLYFSDIRS
    If FolderExists(sInitFolder) Then bi.lpfnCallback = PtrToFunction(AddressOf BFFCallback)
    bi.lParam = StrPtr(sInitFolder)
    
    pItem = SHBrowseForFolder(bi)
    
    If pItem Then ' Succeeded
    sFullPath = Space$(MAX_PATH)
    If SHGetPathFromIDList(pItem, sFullPath) Then
    ReturnPath = Left$(sFullPath, InStr(sFullPath, vbNullChar) - 1) ' Strip nulls
    CoTaskMemFree pItem
    End If
    End If
    
    If ReturnPath <> "" Then
    If Right$(ReturnPath, 1) <> "\" Then
    ReturnPath = ReturnPath & "\"
    End If
    End If
    
    FolderBrowse = ReturnPath

End Function

' typedef int (CALLBACK* BFFCALLBACK)(HWND hwnd, UINT uMsg, LPARAM lParam, LPARAM lpData);
Private Function BFFCallback(ByVal Hwnd As LongPtr, ByVal uMsg As LongPtr, ByVal lParam As LongPtr, ByVal sData As String) As LongPtr
    If uMsg = BFFM_INITIALIZED Then
        SendMessageA Hwnd, BFFM_SETSELECTIONA, True, ByVal sData
    End If
End Function

Private Function PtrToFunction(ByVal lFcnPtr As LongPtr) As LongPtr
    PtrToFunction = lFcnPtr
End Function

Private Function CorrectPath(ByVal sPath As String) As String
    If Right$(sPath, 1) = "\" Then
        If Len(sPath) > 3 Then sPath = Left$(sPath, Len(sPath) - 1) ' Strip backslash from non-root
    Else
        If Len(sPath) = 2 Then sPath = sPath & "\" ' Append backslash to root
    End If
    CorrectPath = sPath
End Function

Public Function FolderExists(ByVal sFolderName As String) As Boolean
    Dim att As Long
    On Error Resume Next
    att = GetAttr(sFolderName)
    If err.Number = 0 Then
        FolderExists = True
    Else
        err.Clear
        FolderExists = False
    End If
    On Error GoTo 0
End Function

#End If

Attribute VB_Name = "Elements"
Option Explicit

Public Function ConstructPrimitive(theBody As Body, prt As Part, GDMLfile As DOMDocument60, sldsElem As IXMLDOMNode, newName As String) As IXMLDOMNode

    ' We assume that there is only one shape
    Dim shp As Shape
    Set shp = theBody.Shapes.Item(1)

    Dim filter As String

    ' Polycone - ???
    ' Polyhedra - ???

    filter = "G4Box."
    If (Left(shp.Name, Len(filter)) = filter) Then Set ConstructPrimitive = ConstructBox(theBody, prt, GDMLfile, sldsElem, newName)
    filter = "G4Cons."
    If (Left(shp.Name, Len(filter)) = filter) Then Set ConstructPrimitive = ConstructCons(theBody, prt, GDMLfile, sldsElem, newName)
    filter = "G4Ellipsoid."
    If (Left(shp.Name, Len(filter)) = filter) Then Set ConstructPrimitive = ConstructEllipsoid(theBody, prt, GDMLfile, sldsElem, newName)
    filter = "G4EllipticalCone."
    If (Left(shp.Name, Len(filter)) = filter) Then Set ConstructPrimitive = ConstructEllipticalCone(theBody, prt, GDMLfile, sldsElem, newName)
    filter = "G4EllipticalTube."
    If (Left(shp.Name, Len(filter)) = filter) Then Set ConstructPrimitive = ConstructEllipticalTube(theBody, prt, GDMLfile, sldsElem, newName)
    ' Hedra - ???
    filter = "G4Orb."
    If (Left(shp.Name, Len(filter)) = filter) Then Set ConstructPrimitive = ConstructOrb(theBody, prt, GDMLfile, sldsElem, newName)
    filter = "G4Para."
    If (Left(shp.Name, Len(filter)) = filter) Then Set ConstructPrimitive = ConstructPara(theBody, prt, GDMLfile, sldsElem, newName)
    filter = "G4Sphere."
    If (Left(shp.Name, Len(filter)) = filter) Then Set ConstructPrimitive = ConstructSphere(theBody, prt, GDMLfile, sldsElem, newName)
    filter = "G4Torus."
    If (Left(shp.Name, Len(filter)) = filter) Then Set ConstructPrimitive = ConstructTorus(theBody, prt, GDMLfile, sldsElem, newName)
    filter = "G4Trap."
    If (Left(shp.Name, Len(filter)) = filter) Then Set ConstructPrimitive = ConstructTrap(theBody, prt, GDMLfile, sldsElem, newName)
    filter = "G4Trd."
    If (Left(shp.Name, Len(filter)) = filter) Then Set ConstructPrimitive = ConstructTrd(theBody, prt, GDMLfile, sldsElem, newName)
    filter = "G4Tubs."
    If (Left(shp.Name, Len(filter)) = filter) Then Set ConstructPrimitive = ConstructTubs(theBody, prt, GDMLfile, sldsElem, newName)
    filter = "G4TwistedBox."
    If (Left(shp.Name, Len(filter)) = filter) Then Set ConstructPrimitive = ConstructTwistedBox(theBody, prt, GDMLfile, sldsElem, newName)
    filter = "G4TwistedTrap."
    If (Left(shp.Name, Len(filter)) = filter) Then Set ConstructPrimitive = ConstructTwistedTrap(theBody, prt, GDMLfile, sldsElem, newName)
    filter = "G4TwistedTrd."
    If (Left(shp.Name, Len(filter)) = filter) Then Set ConstructPrimitive = ConstructTwistedTrd(theBody, prt, GDMLfile, sldsElem, newName)
    filter = "G4TwistedTubs."
    If (Left(shp.Name, Len(filter)) = filter) Then Set ConstructPrimitive = ConstructTwistedTubs(theBody, prt, GDMLfile, sldsElem, newName)
    filter = "G4Arb8_2."
    If (Left(shp.Name, Len(filter)) = filter) Then Set ConstructPrimitive = ConstructArb(theBody, prt, GDMLfile, sldsElem, newName)
    filter = "G4Xtru2sec."
    If (Left(shp.Name, Len(filter)) = filter) Then Set ConstructPrimitive = ConstructXtru2sec(theBody, prt, GDMLfile, sldsElem, newName)

    'TODO catch unknown shapes

End Function

Private Function ConstructBox(theBody As Body, prt As Part, GDMLfile As DOMDocument60, sldsElem As IXMLDOMNode, newName As String) As IXMLDOMNode

    ' Number of primitive parameters and names as they are in CATIA
    Dim NprimitiveParams As Integer
    NprimitiveParams = 3
    Dim listOfPrimitiveParamNames(2) As String
    listOfPrimitiveParamNames(0) = "pX"
    listOfPrimitiveParamNames(1) = "pY"
    listOfPrimitiveParamNames(2) = "pZ"
    Dim listOfPrimitiveParamValues(2) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Box: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("box"))
    Support.createAttribute GDMLfile, theNode, "name", newName
    Support.createAttribute GDMLfile, theNode, "x", MultiplyByTwo(listOfPrimitiveParamValues(0))
    Support.createAttribute GDMLfile, theNode, "y", MultiplyByTwo(listOfPrimitiveParamValues(1))
    Support.createAttribute GDMLfile, theNode, "z", MultiplyByTwo(listOfPrimitiveParamValues(2))
    Support.createAttribute GDMLfile, theNode, "lunit", "mm"
    
    ' Return statement
    Set ConstructBox = theNode

End Function

Private Function ConstructCons(theBody As Body, prt As Part, GDMLfile As DOMDocument60, sldsElem As IXMLDOMNode, newName As String) As IXMLDOMNode

    ' Number of primitive parameters and names as they are in CATIA
    Dim NprimitiveParams As Integer
    NprimitiveParams = 7
    Dim listOfPrimitiveParamNames(6) As String
    listOfPrimitiveParamNames(0) = "pRmin1"
    listOfPrimitiveParamNames(1) = "pRmax1"
    listOfPrimitiveParamNames(2) = "pRmin2"
    listOfPrimitiveParamNames(3) = "pRmax2"
    listOfPrimitiveParamNames(4) = "pDz"
    listOfPrimitiveParamNames(5) = "pSPhi"
    listOfPrimitiveParamNames(6) = "pDPhi"
    Dim listOfPrimitiveParamValues(6) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Cons: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("cone"))
    Support.createAttribute GDMLfile, theNode, "name", newName
    Support.createAttribute GDMLfile, theNode, "rmin1", listOfPrimitiveParamValues(0)
    Support.createAttribute GDMLfile, theNode, "rmax1", listOfPrimitiveParamValues(1)
    Support.createAttribute GDMLfile, theNode, "rmin2", listOfPrimitiveParamValues(2)
    Support.createAttribute GDMLfile, theNode, "rmax2", listOfPrimitiveParamValues(3)
    Support.createAttribute GDMLfile, theNode, "z", MultiplyByTwo(listOfPrimitiveParamValues(4))
    Support.createAttribute GDMLfile, theNode, "startphi", listOfPrimitiveParamValues(5)
    Support.createAttribute GDMLfile, theNode, "deltaphi", listOfPrimitiveParamValues(6)
    Support.createAttribute GDMLfile, theNode, "aunit", "deg"
    Support.createAttribute GDMLfile, theNode, "lunit", "mm"
    
    ' Return statement
    Set ConstructCons = theNode

End Function

Private Function ConstructEllipsoid(theBody As Body, prt As Part, GDMLfile As DOMDocument60, sldsElem As IXMLDOMNode, newName As String) As IXMLDOMNode

    ' Number of primitive parameters and names as they are in CATIA
    Dim NprimitiveParams As Integer
    NprimitiveParams = 5
    Dim listOfPrimitiveParamNames(4) As String
    listOfPrimitiveParamNames(0) = "pxSemiAxis"
    listOfPrimitiveParamNames(1) = "pySemiAxis"
    listOfPrimitiveParamNames(2) = "pzSemiAxis"
    listOfPrimitiveParamNames(3) = "pzBottomCut"
    listOfPrimitiveParamNames(4) = "pzTopCut"
    Dim listOfPrimitiveParamValues(4) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Ellipsoid: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("ellipsoid"))
    Support.createAttribute GDMLfile, theNode, "name", newName
    Support.createAttribute GDMLfile, theNode, "ax", listOfPrimitiveParamValues(0)
    Support.createAttribute GDMLfile, theNode, "by", listOfPrimitiveParamValues(1)
    Support.createAttribute GDMLfile, theNode, "cz", listOfPrimitiveParamValues(2)
    Support.createAttribute GDMLfile, theNode, "zcut1", listOfPrimitiveParamValues(3)
    Support.createAttribute GDMLfile, theNode, "zcut2", listOfPrimitiveParamValues(4)
    Support.createAttribute GDMLfile, theNode, "lunit", "mm"
    
    ' Return statement
    Set ConstructEllipsoid = theNode

End Function

Private Function ConstructEllipticalCone(theBody As Body, prt As Part, GDMLfile As DOMDocument60, sldsElem As IXMLDOMNode, newName As String) As IXMLDOMNode

    ' Number of primitive parameters and names as they are in CATIA
    Dim NprimitiveParams As Integer
    NprimitiveParams = 4
    Dim listOfPrimitiveParamNames(3) As String
    listOfPrimitiveParamNames(0) = "pxSemiAxis"
    listOfPrimitiveParamNames(1) = "pySemiAxis"
    listOfPrimitiveParamNames(2) = "zMax"
    listOfPrimitiveParamNames(3) = "pzTopCut"
    Dim listOfPrimitiveParamValues(3) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "EllipticalCone: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Patch should be checked. It will only work for zmax=zcut by now
    Dim dxStr As String
    Dim dyStr As String
    dxStr = "(" + listOfPrimitiveParamValues(0) + ")/" + listOfPrimitiveParamValues(2)
    dyStr = "(" + listOfPrimitiveParamValues(1) + ")/" + listOfPrimitiveParamValues(2)

    ' Create a tag in GDML file. Names as they are in GDML.
    Dim theNode As IXMLDOMElement
    Set theNode = sldsElem.appendChild(GDMLfile.createElement("elcone"))
    Support.createAttribute GDMLfile, theNode, "name", newName
    Support.createAttribute GDMLfile, theNode, "dx", dxStr
    Support.createAttribute GDMLfile, theNode, "dy", dyStr
    Support.createAttribute GDMLfile, theNode, "zmax", DivideByTwo(listOfPrimitiveParamValues(2))
    Support.createAttribute GDMLfile, theNode, "zcut", DivideByTwo(listOfPrimitiveParamValues(3))
    Support.createAttribute GDMLfile, theNode, "lunit", "mm"
    
    ' Return statement
    Set ConstructEllipticalCone = theNode

End Function

Private Function ConstructEllipticalTube(theBody As Body, prt As Part, GDMLfile As DOMDocument60, sldsElem As IXMLDOMNode, newName As String) As IXMLDOMNode

    ' Number of primitive parameters and names as they are in CATIA
    Dim NprimitiveParams As Integer
    NprimitiveParams = 3
    Dim listOfPrimitiveParamNames(2) As String
    listOfPrimitiveParamNames(0) = "Dx"
    listOfPrimitiveParamNames(1) = "Dy"
    listOfPrimitiveParamNames(2) = "Dz"
    Dim listOfPrimitiveParamValues(2) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "EllipticalTube: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("eltube"))
    Support.createAttribute GDMLfile, theNode, "name", newName
    Support.createAttribute GDMLfile, theNode, "dx", listOfPrimitiveParamValues(0)
    Support.createAttribute GDMLfile, theNode, "dy", listOfPrimitiveParamValues(1)
    Support.createAttribute GDMLfile, theNode, "dz", listOfPrimitiveParamValues(2)
    Support.createAttribute GDMLfile, theNode, "lunit", "mm"
    
    ' Return statement
    Set ConstructEllipticalTube = theNode

End Function

Private Function ConstructOrb(theBody As Body, prt As Part, GDMLfile As DOMDocument60, sldsElem As IXMLDOMNode, newName As String) As IXMLDOMNode

    ' Number of primitive parameters and names as they are in CATIA
    Dim NprimitiveParams As Integer
    NprimitiveParams = 1
    Dim listOfPrimitiveParamNames(0) As String
    listOfPrimitiveParamNames(0) = "pRmax"
    Dim listOfPrimitiveParamValues(0) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Orb: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("orb"))
    Support.createAttribute GDMLfile, theNode, "name", newName
    Support.createAttribute GDMLfile, theNode, "r", listOfPrimitiveParamValues(0)
    Support.createAttribute GDMLfile, theNode, "lunit", "mm"
    
    ' Return statement
    Set ConstructOrb = theNode

End Function

Private Function ConstructPara(theBody As Body, prt As Part, GDMLfile As DOMDocument60, sldsElem As IXMLDOMNode, newName As String) As IXMLDOMNode

    ' Number of primitive parameters and names as they are in CATIA
    Dim NprimitiveParams As Integer
    NprimitiveParams = 6
    Dim listOfPrimitiveParamNames(5) As String
    listOfPrimitiveParamNames(0) = "dx"
    listOfPrimitiveParamNames(1) = "dy"
    listOfPrimitiveParamNames(2) = "dz"
    listOfPrimitiveParamNames(3) = "alpha"
    listOfPrimitiveParamNames(4) = "theta"
    listOfPrimitiveParamNames(5) = "phi"
    Dim listOfPrimitiveParamValues(5) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Para: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("para"))
    Support.createAttribute GDMLfile, theNode, "name", newName
    Support.createAttribute GDMLfile, theNode, "x", MultiplyByTwo(listOfPrimitiveParamValues(0))
    Support.createAttribute GDMLfile, theNode, "y", MultiplyByTwo(listOfPrimitiveParamValues(1))
    Support.createAttribute GDMLfile, theNode, "z", MultiplyByTwo(listOfPrimitiveParamValues(2))
    Support.createAttribute GDMLfile, theNode, "alpha", listOfPrimitiveParamValues(3)
    Support.createAttribute GDMLfile, theNode, "theta", listOfPrimitiveParamValues(4)
    Support.createAttribute GDMLfile, theNode, "phi", listOfPrimitiveParamValues(5)
    Support.createAttribute GDMLfile, theNode, "aunit", "deg"
    Support.createAttribute GDMLfile, theNode, "lunit", "mm"
    
    ' Return statement
    Set ConstructPara = theNode

End Function

Private Function ConstructSphere(theBody As Body, prt As Part, GDMLfile As DOMDocument60, sldsElem As IXMLDOMNode, newName As String) As IXMLDOMNode

    ' Number of primitive parameters and names as they are in CATIA
    Dim NprimitiveParams As Integer
    NprimitiveParams = 6
    Dim listOfPrimitiveParamNames(5) As String
    listOfPrimitiveParamNames(0) = "pRmin"
    listOfPrimitiveParamNames(1) = "pRmax"
    listOfPrimitiveParamNames(2) = "pSPhi"
    listOfPrimitiveParamNames(3) = "pDPhi"
    listOfPrimitiveParamNames(4) = "pSTheta"
    listOfPrimitiveParamNames(5) = "pDTheta"
    Dim listOfPrimitiveParamValues(5) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Sphere: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("sphere"))
    Support.createAttribute GDMLfile, theNode, "name", newName
    Support.createAttribute GDMLfile, theNode, "rmin", listOfPrimitiveParamValues(0)
    Support.createAttribute GDMLfile, theNode, "rmax", listOfPrimitiveParamValues(1)
    Support.createAttribute GDMLfile, theNode, "startphi", listOfPrimitiveParamValues(2)
    Support.createAttribute GDMLfile, theNode, "deltaphi", listOfPrimitiveParamValues(3)
    Support.createAttribute GDMLfile, theNode, "starttheta", listOfPrimitiveParamValues(4)
    Support.createAttribute GDMLfile, theNode, "deltatheta", listOfPrimitiveParamValues(5)
    Support.createAttribute GDMLfile, theNode, "aunit", "deg"
    Support.createAttribute GDMLfile, theNode, "lunit", "mm"
    
    ' Return statement
    Set ConstructSphere = theNode

End Function

Private Function ConstructTorus(theBody As Body, prt As Part, GDMLfile As DOMDocument60, sldsElem As IXMLDOMNode, newName As String) As IXMLDOMNode

    ' Number of primitive parameters and names as they are in CATIA
    Dim NprimitiveParams As Integer
    NprimitiveParams = 5
    Dim listOfPrimitiveParamNames(4) As String
    listOfPrimitiveParamNames(0) = "pRmin"
    listOfPrimitiveParamNames(1) = "pRmax"
    listOfPrimitiveParamNames(2) = "pRtor"
    listOfPrimitiveParamNames(3) = "pSPhi"
    listOfPrimitiveParamNames(4) = "pDPhi"
    Dim listOfPrimitiveParamValues(4) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Torus: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("torus"))
    Support.createAttribute GDMLfile, theNode, "name", newName
    Support.createAttribute GDMLfile, theNode, "rmin", listOfPrimitiveParamValues(0)
    Support.createAttribute GDMLfile, theNode, "rmax", listOfPrimitiveParamValues(1)
    Support.createAttribute GDMLfile, theNode, "rtor", listOfPrimitiveParamValues(2)
    Support.createAttribute GDMLfile, theNode, "startphi", listOfPrimitiveParamValues(3)
    Support.createAttribute GDMLfile, theNode, "deltaphi", listOfPrimitiveParamValues(4)
    Support.createAttribute GDMLfile, theNode, "aunit", "deg"
    Support.createAttribute GDMLfile, theNode, "lunit", "mm"
    
    ' Return statement
    Set ConstructTorus = theNode

End Function

Private Function ConstructTrap(theBody As Body, prt As Part, GDMLfile As DOMDocument60, sldsElem As IXMLDOMNode, newName As String) As IXMLDOMNode

    ' Number of primitive parameters and names as they are in CATIA
    Dim NprimitiveParams As Integer
    NprimitiveParams = 10
    Dim listOfPrimitiveParamNames(9) As String
    listOfPrimitiveParamNames(0) = "pDz"
    listOfPrimitiveParamNames(1) = "pTheta"
    listOfPrimitiveParamNames(2) = "pPhi"
    listOfPrimitiveParamNames(3) = "pDy1"
    listOfPrimitiveParamNames(4) = "pDx1"
    listOfPrimitiveParamNames(5) = "pDx2"
    listOfPrimitiveParamNames(6) = "pAlp1"
    listOfPrimitiveParamNames(7) = "pDy2"
    listOfPrimitiveParamNames(8) = "pDx3"
    listOfPrimitiveParamNames(9) = "pDx4"
    Dim listOfPrimitiveParamValues(9) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Trap: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("trap"))
    Support.createAttribute GDMLfile, theNode, "name", newName
    Support.createAttribute GDMLfile, theNode, "z", MultiplyByTwo(listOfPrimitiveParamValues(0))
    Support.createAttribute GDMLfile, theNode, "theta", listOfPrimitiveParamValues(1)
    Support.createAttribute GDMLfile, theNode, "phi", listOfPrimitiveParamValues(2)
    Support.createAttribute GDMLfile, theNode, "y1", MultiplyByTwo(listOfPrimitiveParamValues(3))
    Support.createAttribute GDMLfile, theNode, "x1", MultiplyByTwo(listOfPrimitiveParamValues(4))
    Support.createAttribute GDMLfile, theNode, "x2", MultiplyByTwo(listOfPrimitiveParamValues(5))
    Support.createAttribute GDMLfile, theNode, "alpha1", listOfPrimitiveParamValues(6)
    Support.createAttribute GDMLfile, theNode, "y2", MultiplyByTwo(listOfPrimitiveParamValues(7))
    Support.createAttribute GDMLfile, theNode, "x3", MultiplyByTwo(listOfPrimitiveParamValues(8))
    Support.createAttribute GDMLfile, theNode, "x4", MultiplyByTwo(listOfPrimitiveParamValues(9))
    Support.createAttribute GDMLfile, theNode, "alpha2", listOfPrimitiveParamValues(6)  ' yes....
    Support.createAttribute GDMLfile, theNode, "aunit", "deg"
    Support.createAttribute GDMLfile, theNode, "lunit", "mm"
    
    ' Return statement
    Set ConstructTrap = theNode

End Function

Private Function ConstructTrd(theBody As Body, prt As Part, GDMLfile As DOMDocument60, sldsElem As IXMLDOMNode, newName As String) As IXMLDOMNode

    ' Number of primitive parameters and names as they are in CATIA
    Dim NprimitiveParams As Integer
    NprimitiveParams = 5
    Dim listOfPrimitiveParamNames(4) As String
    listOfPrimitiveParamNames(0) = "dx1"
    listOfPrimitiveParamNames(1) = "dy1"
    listOfPrimitiveParamNames(2) = "dx2"
    listOfPrimitiveParamNames(3) = "dy2"
    listOfPrimitiveParamNames(4) = "dz"
    Dim listOfPrimitiveParamValues(4) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Trd: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("trd"))
    Support.createAttribute GDMLfile, theNode, "name", newName
    Support.createAttribute GDMLfile, theNode, "x1", MultiplyByTwo(listOfPrimitiveParamValues(0))
    Support.createAttribute GDMLfile, theNode, "y1", MultiplyByTwo(listOfPrimitiveParamValues(1))
    Support.createAttribute GDMLfile, theNode, "x2", MultiplyByTwo(listOfPrimitiveParamValues(2))
    Support.createAttribute GDMLfile, theNode, "y2", MultiplyByTwo(listOfPrimitiveParamValues(3))
    Support.createAttribute GDMLfile, theNode, "z", MultiplyByTwo(listOfPrimitiveParamValues(4))
    Support.createAttribute GDMLfile, theNode, "lunit", "mm"
    
    ' Return statement
    Set ConstructTrd = theNode

End Function

Private Function ConstructTubs(theBody As Body, prt As Part, GDMLfile As DOMDocument60, sldsElem As IXMLDOMNode, newName As String) As IXMLDOMNode

    ' Number of primitive parameters and names as they are in CATIA
    Dim NprimitiveParams As Integer
    NprimitiveParams = 5
    Dim listOfPrimitiveParamNames(4) As String
    listOfPrimitiveParamNames(0) = "pRMin"
    listOfPrimitiveParamNames(1) = "pRMax"
    listOfPrimitiveParamNames(2) = "pDz"
    listOfPrimitiveParamNames(3) = "pSPhi"
    listOfPrimitiveParamNames(4) = "pDPhi"
    Dim listOfPrimitiveParamValues(4) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Tubs: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("tube"))
    Support.createAttribute GDMLfile, theNode, "name", newName
    Support.createAttribute GDMLfile, theNode, "rmin", listOfPrimitiveParamValues(0)
    Support.createAttribute GDMLfile, theNode, "rmax", listOfPrimitiveParamValues(1)
    Support.createAttribute GDMLfile, theNode, "z", MultiplyByTwo(listOfPrimitiveParamValues(2))
    Support.createAttribute GDMLfile, theNode, "startphi", listOfPrimitiveParamValues(3)
    Support.createAttribute GDMLfile, theNode, "deltaphi", listOfPrimitiveParamValues(4)
    Support.createAttribute GDMLfile, theNode, "aunit", "deg"
    Support.createAttribute GDMLfile, theNode, "lunit", "mm"
    
    ' Return statement
    Set ConstructTubs = theNode

End Function

Private Function ConstructTwistedBox(theBody As Body, prt As Part, GDMLfile As DOMDocument60, sldsElem As IXMLDOMNode, newName As String) As IXMLDOMNode

    ' Number of primitive parameters and names as they are in CATIA
    Dim NprimitiveParams As Integer
    NprimitiveParams = 4
    Dim listOfPrimitiveParamNames(3) As String
    listOfPrimitiveParamNames(0) = "twistedangle"
    listOfPrimitiveParamNames(1) = "pDx"
    listOfPrimitiveParamNames(2) = "pDy"
    listOfPrimitiveParamNames(3) = "pDz"
    Dim listOfPrimitiveParamValues(3) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "TwistedBox: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("twistedbox"))
    Support.createAttribute GDMLfile, theNode, "name", newName
    Support.createAttribute GDMLfile, theNode, "PhiTwist", listOfPrimitiveParamValues(0)
    Support.createAttribute GDMLfile, theNode, "x", MultiplyByTwo(listOfPrimitiveParamValues(1))
    Support.createAttribute GDMLfile, theNode, "y", MultiplyByTwo(listOfPrimitiveParamValues(2))
    Support.createAttribute GDMLfile, theNode, "z", MultiplyByTwo(listOfPrimitiveParamValues(3))
    Support.createAttribute GDMLfile, theNode, "aunit", "deg"
    Support.createAttribute GDMLfile, theNode, "lunit", "mm"
    
    ' Return statement
    Set ConstructTwistedBox = theNode

End Function

Private Function ConstructTwistedTrap(theBody As Body, prt As Part, GDMLfile As DOMDocument60, sldsElem As IXMLDOMNode, newName As String) As IXMLDOMNode

    ' Number of primitive parameters and names as they are in CATIA
    Dim NprimitiveParams As Integer
    NprimitiveParams = 11
    Dim listOfPrimitiveParamNames(10) As String
    listOfPrimitiveParamNames(0) = "twistedangle"
    listOfPrimitiveParamNames(1) = "pDz"
    listOfPrimitiveParamNames(2) = "pTheta"
    listOfPrimitiveParamNames(3) = "pPhi"
    listOfPrimitiveParamNames(4) = "pDy1"
    listOfPrimitiveParamNames(5) = "pDx1"
    listOfPrimitiveParamNames(6) = "pDx2"
    listOfPrimitiveParamNames(7) = "pDy2"
    listOfPrimitiveParamNames(8) = "pDx3"
    listOfPrimitiveParamNames(9) = "pDx4"
    listOfPrimitiveParamNames(10) = "pAlph"
    Dim listOfPrimitiveParamValues(10) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "TwistedTrap: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("twistedtrap"))
    Support.createAttribute GDMLfile, theNode, "name", newName
    Support.createAttribute GDMLfile, theNode, "PhiTwist", listOfPrimitiveParamValues(0)
    Support.createAttribute GDMLfile, theNode, "z", MultiplyByTwo(listOfPrimitiveParamValues(1))
    Support.createAttribute GDMLfile, theNode, "Theta", listOfPrimitiveParamValues(2)
    Support.createAttribute GDMLfile, theNode, "Phi", listOfPrimitiveParamValues(3)
    Support.createAttribute GDMLfile, theNode, "y1", MultiplyByTwo(listOfPrimitiveParamValues(4))
    Support.createAttribute GDMLfile, theNode, "x1", MultiplyByTwo(listOfPrimitiveParamValues(5))
    Support.createAttribute GDMLfile, theNode, "x2", MultiplyByTwo(listOfPrimitiveParamValues(6))
    Support.createAttribute GDMLfile, theNode, "y2", MultiplyByTwo(listOfPrimitiveParamValues(7))
    Support.createAttribute GDMLfile, theNode, "x3", MultiplyByTwo(listOfPrimitiveParamValues(8))
    Support.createAttribute GDMLfile, theNode, "x4", MultiplyByTwo(listOfPrimitiveParamValues(9))
    Support.createAttribute GDMLfile, theNode, "Alph", listOfPrimitiveParamValues(10)
    Support.createAttribute GDMLfile, theNode, "aunit", "deg"
    Support.createAttribute GDMLfile, theNode, "lunit", "mm"
    
    ' Return statement
    Set ConstructTwistedTrap = theNode

End Function

Private Function ConstructTwistedTrd(theBody As Body, prt As Part, GDMLfile As DOMDocument60, sldsElem As IXMLDOMNode, newName As String) As IXMLDOMNode

    ' Number of primitive parameters and names as they are in CATIA
    Dim NprimitiveParams As Integer
    NprimitiveParams = 6
    Dim listOfPrimitiveParamNames(5) As String
    listOfPrimitiveParamNames(0) = "pDx1"
    listOfPrimitiveParamNames(1) = "pDx2"
    listOfPrimitiveParamNames(2) = "pDy1"
    listOfPrimitiveParamNames(3) = "pDy2"
    listOfPrimitiveParamNames(4) = "pDz"
    listOfPrimitiveParamNames(5) = "twistedangle"
    Dim listOfPrimitiveParamValues(5) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "TwistedTrd: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("twistedtrd"))
    Support.createAttribute GDMLfile, theNode, "name", newName
    Support.createAttribute GDMLfile, theNode, "PhiTwisted", listOfPrimitiveParamValues(5)
    Support.createAttribute GDMLfile, theNode, "x1", listOfPrimitiveParamValues(0)
    Support.createAttribute GDMLfile, theNode, "x2", listOfPrimitiveParamValues(1)
    Support.createAttribute GDMLfile, theNode, "y1", listOfPrimitiveParamValues(2)
    Support.createAttribute GDMLfile, theNode, "y2", listOfPrimitiveParamValues(3)
    Support.createAttribute GDMLfile, theNode, "z", MultiplyByTwo(listOfPrimitiveParamValues(4))
    Support.createAttribute GDMLfile, theNode, "aunit", "deg"
    Support.createAttribute GDMLfile, theNode, "lunit", "mm"
    
    ' Return statement
    Set ConstructTwistedTrd = theNode

End Function

Private Function ConstructTwistedTubs(theBody As Body, prt As Part, GDMLfile As DOMDocument60, sldsElem As IXMLDOMNode, newName As String) As IXMLDOMNode

    ' Number of primitive parameters and names as they are in CATIA
    Dim NprimitiveParams As Integer
    NprimitiveParams = 5
    Dim listOfPrimitiveParamNames(4) As String
    listOfPrimitiveParamNames(0) = "twistedangle"
    listOfPrimitiveParamNames(1) = "endinnerrad"
    listOfPrimitiveParamNames(2) = "endouterrad"
    listOfPrimitiveParamNames(3) = "halfzlen"
    listOfPrimitiveParamNames(4) = "dphi"
    Dim listOfPrimitiveParamValues(4) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "TwistedTubs: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("twistedtubs"))
    Support.createAttribute GDMLfile, theNode, "name", newName
    Support.createAttribute GDMLfile, theNode, "endinnerrad", listOfPrimitiveParamValues(1)
    Support.createAttribute GDMLfile, theNode, "endouterrad", listOfPrimitiveParamValues(2)
    Support.createAttribute GDMLfile, theNode, "zlen", MultiplyByTwo(listOfPrimitiveParamValues(3))
    Support.createAttribute GDMLfile, theNode, "twistedangle", listOfPrimitiveParamValues(0)
    Support.createAttribute GDMLfile, theNode, "phi", listOfPrimitiveParamValues(4)
    Support.createAttribute GDMLfile, theNode, "aunit", "deg"
    Support.createAttribute GDMLfile, theNode, "lunit", "mm"
    
    ' Return statement
    Set ConstructTwistedTubs = theNode

End Function

Private Function ConstructArb(theBody As Body, prt As Part, GDMLfile As DOMDocument60, sldsElem As IXMLDOMNode, newName As String) As IXMLDOMNode

    ' Number of primitive parameters and names as they are in CATIA
    Dim NprimitiveParams As Integer
    NprimitiveParams = 17
    Dim listOfPrimitiveParamNames(16) As String
    listOfPrimitiveParamNames(0) = "v1x"
    listOfPrimitiveParamNames(1) = "v1y"
    listOfPrimitiveParamNames(2) = "v2x"
    listOfPrimitiveParamNames(3) = "v2y"
    listOfPrimitiveParamNames(4) = "v3x"
    listOfPrimitiveParamNames(5) = "v3y"
    listOfPrimitiveParamNames(6) = "v4x"
    listOfPrimitiveParamNames(7) = "v4y"
    listOfPrimitiveParamNames(8) = "v5x"
    listOfPrimitiveParamNames(9) = "v5y"
    listOfPrimitiveParamNames(10) = "v6x"
    listOfPrimitiveParamNames(11) = "v6y"
    listOfPrimitiveParamNames(12) = "v7x"
    listOfPrimitiveParamNames(13) = "v7y"
    listOfPrimitiveParamNames(14) = "v8x"
    listOfPrimitiveParamNames(15) = "v8y"
    listOfPrimitiveParamNames(16) = "dz"
    Dim listOfPrimitiveParamValues(16) As String
    
    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Arb8: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam
    
    ' Create a tag in GDML file. Names as they are in GDML.
    Dim theNode As IXMLDOMElement
    Set theNode = sldsElem.appendChild(GDMLfile.createElement("arb8"))
    Support.createAttribute GDMLfile, theNode, "name", newName
    Support.createAttribute GDMLfile, theNode, "v1x", listOfPrimitiveParamValues(0)
    Support.createAttribute GDMLfile, theNode, "v1y", listOfPrimitiveParamValues(1)
    Support.createAttribute GDMLfile, theNode, "v2x", listOfPrimitiveParamValues(2)
    Support.createAttribute GDMLfile, theNode, "v2y", listOfPrimitiveParamValues(3)
    Support.createAttribute GDMLfile, theNode, "v3x", listOfPrimitiveParamValues(4)
    Support.createAttribute GDMLfile, theNode, "v3y", listOfPrimitiveParamValues(5)
    Support.createAttribute GDMLfile, theNode, "v4x", listOfPrimitiveParamValues(6)
    Support.createAttribute GDMLfile, theNode, "v4y", listOfPrimitiveParamValues(7)
    Support.createAttribute GDMLfile, theNode, "v5x", listOfPrimitiveParamValues(8)
    Support.createAttribute GDMLfile, theNode, "v5y", listOfPrimitiveParamValues(9)
    Support.createAttribute GDMLfile, theNode, "v6x", listOfPrimitiveParamValues(10)
    Support.createAttribute GDMLfile, theNode, "v6y", listOfPrimitiveParamValues(11)
    Support.createAttribute GDMLfile, theNode, "v7x", listOfPrimitiveParamValues(12)
    Support.createAttribute GDMLfile, theNode, "v7y", listOfPrimitiveParamValues(13)
    Support.createAttribute GDMLfile, theNode, "v8x", listOfPrimitiveParamValues(14)
    Support.createAttribute GDMLfile, theNode, "v8y", listOfPrimitiveParamValues(15)
    Support.createAttribute GDMLfile, theNode, "dz", listOfPrimitiveParamValues(16)
    Support.createAttribute GDMLfile, theNode, "lunit", "mm"
    
    ' Return statement
    Set ConstructArb = theNode

End Function

Private Function ConstructXtru2sec(theBody As Body, prt As Part, GDMLfile As DOMDocument60, sldsElem As IXMLDOMNode, newName As String) As IXMLDOMNode

    ' Number of primitive parameters and names as they are in CATIA
    Dim NprimitiveParams As Integer
    NprimitiveParams = 8
    Dim listOfPrimitiveParamNames(7) As String
    listOfPrimitiveParamNames(0) = "z_bottom"
    listOfPrimitiveParamNames(1) = "scale_bottom"
    listOfPrimitiveParamNames(2) = "x_bottom"
    listOfPrimitiveParamNames(3) = "y_bottom"
    listOfPrimitiveParamNames(4) = "z_top"
    listOfPrimitiveParamNames(5) = "scale_top"
    listOfPrimitiveParamNames(6) = "x_top"
    listOfPrimitiveParamNames(7) = "y_top"
    Dim listOfPrimitiveParamValues(7) As String

    ' Actually parse the CATIA parameters and extract parameters' values/formulae
    Call DoParse(theBody, prt, GDMLfile, sldsElem, NprimitiveParams, listOfPrimitiveParamNames, listOfPrimitiveParamValues)

    ' Debug print
    formCATIA2GDML.ListBox1.AddItem "Xtru2sec: "
    Dim iPrimitiveParam As Integer
    For iPrimitiveParam = 1 To NprimitiveParams
        formCATIA2GDML.ListBox1.AddItem listOfPrimitiveParamNames(iPrimitiveParam - 1) + " = " + listOfPrimitiveParamValues(iPrimitiveParam - 1)
    Next iPrimitiveParam

    ' Create a tag in GDML file. Names as they are in GDML.
    Dim xtruNode As IXMLDOMElement
    Set xtruNode = sldsElem.appendChild(GDMLfile.createElement("xtru"))
    Support.createAttribute GDMLfile, xtruNode, "name", newName
    Support.createAttribute GDMLfile, xtruNode, "lunit", "mm"

    ' Parse the blueprint sketch
    Call FindAndParseSketch(theBody, prt, GDMLfile, xtruNode)

    ' Write out two sections
    Dim sectionChildNode As IXMLDOMElement
    Set sectionChildNode = xtruNode.appendChild(GDMLfile.createElement("section"))
    Support.createAttribute GDMLfile, sectionChildNode, "zOrder", 0
    Support.createAttribute GDMLfile, sectionChildNode, "zPosition", listOfPrimitiveParamValues(0)
    Support.createAttribute GDMLfile, sectionChildNode, "xOffset", listOfPrimitiveParamValues(2)
    Support.createAttribute GDMLfile, sectionChildNode, "yOffset", listOfPrimitiveParamValues(3)
    Support.createAttribute GDMLfile, sectionChildNode, "scalingFactor", listOfPrimitiveParamValues(1)
    Set sectionChildNode = xtruNode.appendChild(GDMLfile.createElement("section"))
    Support.createAttribute GDMLfile, sectionChildNode, "zOrder", 1
    Support.createAttribute GDMLfile, sectionChildNode, "zPosition", listOfPrimitiveParamValues(4)
    Support.createAttribute GDMLfile, sectionChildNode, "xOffset", listOfPrimitiveParamValues(6)
    Support.createAttribute GDMLfile, sectionChildNode, "yOffset", listOfPrimitiveParamValues(7)
    Support.createAttribute GDMLfile, sectionChildNode, "scalingFactor", listOfPrimitiveParamValues(5)

    ' Return statement
    Set ConstructXtru2sec = xtruNode

End Function

' Find and parse the blueprint sketch for the Xtru2sec primitive
Private Sub FindAndParseSketch(theBody As Body, prt As Part, GDMLfile As DOMDocument60, xtruNode As IXMLDOMNode)

    ' We assume that there is only one shape so take the first one
    Dim shp As Shape
    Set shp = theBody.Shapes.Item(1)

    If (TypeName(shp) <> "ShapeInstance") Then
        MsgBox "The first shape of the body '" & theBody.Name & "' in part '" & prt.Name & "' if not a UDF. Aboring.", vbCritical
        End
    End If

    Dim expectedSuffix As String
    expectedSuffix = "G4Xtru2sec."
    If Not (Left((shp.Name), Len(expectedSuffix)) = expectedSuffix) Then
        'TODO exception
        MsgBox "Expected '" & expectedSuffix & "*' shape, but '" & shp.Name & "' found. Aborting.", vbCritical
        End
    End If

    Dim xtruUDF As ShapeInstance
    Dim blueprintSketch As Sketch
    Dim sketchElems As GeometricElements
    Dim nElems As Integer

    Set xtruUDF = shp
    Set blueprintSketch = xtruUDF.GetInput("Blueprint")
    Set sketchElems = blueprintSketch.GeometricElements
    nElems = sketchElems.Count

    ' =============================================================================================
    ' Per-se parse the sketch

    Dim ListOfLines As New Collection
    Dim curLine As Line2D
    Dim nLines As Integer

    Dim ListOfPoints As New Collection
    Dim curPoint As Point2D
    Dim nPoints As Integer

    nLines = 0
    nPoints = 0

    Dim iElem As Integer

    ' =============================================================================================
    ' Count points and lines
    ' Store all points and lines in the collections with their names as keys
    ' Check that there are no coinciding names
    ' =============================================================================================
    For iElem = 1 To nElems

        If (TypeName(sketchElems.Item(iElem)) = "Line2D") Then

            Set curLine = sketchElems.Item(iElem)
            nLines = nLines + 1 ' just counter lines

            ' check that there were no other lines with the same name before
            If (MyContains(ListOfLines, curLine.Name)) Then
                MsgBox "There are mupliple lines named '" & curLine.Name & "' in the Xtru blueprint sketch '" & _
                    blueprintSketch.Name & "' of part '" & prt.Name & "'. Aborting.", vbCritical
                End
            End If
    
            ' put the line into the list. The name is the key. Names should not coincide.
            ListOfLines.Add sketchElems.Item(iElem), curLine.Name
            formCATIA2GDML.ListBox1.AddItem iElem & ": Line '" & curLine.Name & "'"

        ElseIf (TypeName(sketchElems.Item(iElem)) = "Point2D") Then
            
            Set curPoint = sketchElems.Item(iElem)
            nPoints = nPoints + 1 ' just count points

            ' check that there were no other points with the same name before
            If (MyContains(ListOfPoints, curPoint.Name)) Then
                MsgBox "There are mupliple points named '" & curPoint.Name & "' in the Xtru blueprint sketch '" & _
                    blueprintSketch.Name & "' of part '" & prt.Name & "'. Aborting.", vbCritical
                End
            End If

            ' put the point into the list. The name is the key. Names should not coincide.
            ListOfPoints.Add sketchElems.Item(iElem), curPoint.Name
            formCATIA2GDML.ListBox1.AddItem iElem & ": Point '" & curPoint.Name & "'"

        ElseIf (TypeName(sketchElems.Item(iElem)) = "Axis2D") Then
            ' OK - do nothing
        Else
            'TODO exception
            MsgBox "Xtru2sec blueprint sketch must contain only points and lines. '" & sketchElems.Item(iElem).Name & "' has type '" & _
                TypeName(sketchElems.Item(iElem)) & "' Aborting.", vbCritical
            End
        End If

    Next iElem
    ' =============================================================================================

    ' In the second loop we ignore all other types except Line2D.

    ' Take the start point of the first line as the starting point for the edge loop search
    Set curPoint = ListOfLines(1).startPoint
    ' Store the starting point name
    Dim startingPointName As String
    startingPointName = curPoint.Name

    Dim startPoint As Point2D
    Dim endPoint As Point2D

    Dim iLineIter As Integer
    iLineIter = 0

    ' =============================================================================================

    ' One iteration of the outer loop should correspond to one line of the edge loop
    Do
        ' One iteration of the inner loop corresponds to one line in the full list of lines
        ' If a line found connecting the current point to the next, this line is accounted the
        ' program goes to the next iteration of the outer loop
        'For iElem = 1 To nElems
        '    If (TypeName(sketchElems.Item(iElem)) = "Line2D") Then

        For iElem = 1 To ListOfLines.Count

                Set curLine = ListOfLines.Item(iElem) 'sketchElems.Item(iElem)
                Set startPoint = curLine.startPoint
                Set endPoint = curLine.endPoint
    
                If (curPoint.Name = startPoint.Name) Then
                    formCATIA2GDML.ListBox1.AddItem iLineIter & ": Line '" & curLine.Name & "' - going from start point '" & _
                        startPoint.Name & "' to end point '" & endPoint.Name & "'"
                    Set curPoint = endPoint
                    Call appendPointToXtru(curPoint, GDMLfile, xtruNode)
                    ListOfLines.Remove iElem
                    GoTo NextLineIter
                ElseIf (curPoint.Name = endPoint.Name) Then
                    formCATIA2GDML.ListBox1.AddItem iLineIter & ": Line '" & curLine.Name & "' - going from end point '" & _
                        endPoint.Name & "' to start point '" & startPoint.Name & "'"
                    Set curPoint = startPoint
                    Call appendPointToXtru(curPoint, GDMLfile, xtruNode)
                    ListOfLines.Remove iElem
                    GoTo NextLineIter
                End If
    
        '    End If
        Next iElem

        'TODO exception
        ' In a normal case the program should not reach this line, it should always goto NextIteration
        MsgBox "Could not recognize an edge loop in the blueprint sketch of the Xtru. Aborting.", vbCritical
        End

NextLineIter:
    
        iLineIter = iLineIter + 1
        If (iLineIter > 1000) Then
            MsgBox "Could not recognize an edge loop in the blueprint sketch of the Xtru. Stuck in an infinite loop. Aborting.", vbCritical
            End
        End If

    Loop Until (curPoint.Name = startingPointName)

    'TODO
    ' Clean up - ?

End Sub

Private Sub appendPointToXtru(pnt, GDMLfile As DOMDocument60, xtruNode As IXMLDOMNode)

    Dim coords(0 To 1)
    pnt.GetCoordinates coords

    Dim vertexNode As IXMLDOMElement
    Set vertexNode = xtruNode.appendChild(GDMLfile.createElement("twoDimVertex"))
    Support.createAttribute GDMLfile, vertexNode, "x", Str(coords(0))
    Support.createAttribute GDMLfile, vertexNode, "y", Str(coords(1))

End Sub

' Universal for all primitives
Private Sub DoParse(theBody As Body, prt As Part, GDMLfile As DOMDocument60, sldsElem As IXMLDOMNode, NprimitiveParams As Integer, ByRef listOfPrimitiveParamNames() As String, ByRef listOfPrimitiveParamValues() As String)

    ' We assume that there is only one shape so take the first one
    Dim shp As Shape
    Dim paramFilter As String
    Set shp = theBody.Shapes.Item(1)
    paramFilter = theBody.Name + "\" + shp.Name
    
    Dim partParameters As Parameters
    Set partParameters = prt.Parameters
    
    ' Loop over the parameters of the part
    Dim iParam As Integer
    For iParam = 1 To partParameters.Count
        Dim curParam As Parameter
        Dim curParamValue As String
        Dim curParamRelation As Relation
        Set curParam = partParameters.Item(iParam)
        curParamValue = curParam.ValueAsString
        Set curParamRelation = curParam.OptionalRelation

        ' Find the parameters of the primitve in the parameters of the part
        Dim iPrimitiveParam As Integer
        For iPrimitiveParam = 1 To NprimitiveParams
            If (InStr(1, curParam.Name, paramFilter + "\" + listOfPrimitiveParamNames(iPrimitiveParam - 1)) > 0) Then
                If Not (curParamRelation Is Nothing) Then
                    ' There is a formula for the current parameter - use it, but preprocess!
                    listOfPrimitiveParamValues(iPrimitiveParam - 1) = ProcessFormula(RemoveUnits(curParamRelation.Value))
                Else
                    ' There is no formula for the current parameter - use the value
                    listOfPrimitiveParamValues(iPrimitiveParam - 1) = RemoveUnits(curParamValue)
                End If
            End If
        Next iPrimitiveParam

    Next iParam

End Sub

Attribute VB_Name = "Support"
Option Explicit

Global Const PI = 3.14159265358979

' Just split a path-type string with a delimiter "\" into a collection of separate strings
Public Function ParseParameterName(paramName As String) As Collection

    ' Return object
    Dim parsedParamName As New Collection

    Dim fullStringLen As Integer
    fullStringLen = Len(paramName)

    Dim delim As String
    Dim delimPos As Integer
    Dim subString As String
    Dim curPos As Integer

    delim = "\"
    curPos = 1

    delimPos = InStr(curPos, paramName, delim, vbTextCompare)

    Do While delimPos > 0
        subString = Mid(paramName, curPos, delimPos - curPos)
        parsedParamName.Add subString
        curPos = curPos + Len(subString) + 1
        delimPos = InStr(curPos, paramName, delim, vbTextCompare)
    Loop
    
    parsedParamName.Add Mid(paramName, curPos)

    ' Return statement
    Set ParseParameterName = parsedParamName

End Function

Public Sub createAttribute(XMLDoc As DOMDocument60, myElement As IXMLDOMElement, attributeName As String, attributeValue As String)

    Dim myAttribute As IXMLDOMAttribute
    Set myAttribute = XMLDoc.createAttribute(attributeName)
    myAttribute.Value = attributeValue
    myElement.Attributes.setNamedItem myAttribute

End Sub

'Public Function ValuePrepare(inValue As String) As String
'
'    ' Return object
'    Dim outVal As String
'
'    outVal = Replace(inValue, ",", ".")
'    outVal = Trim(outVal)
'
'    ' Return statement
'    ValuePrepare = outVal
'
'End Function

' Check that the string "key" is in the collection "col"
Public Function Contains(col As Collection, key As String) As Boolean

    Contains = False
    Dim iObj As Integer
    For iObj = 1 To col.Count
        If (col.Item(iObj) = key) Then
            Contains = True
            Exit Function
        End If
    Next iObj
    
End Function

Public Function RemoveUnits(inString As String) As String

    ' Return object
    Dim outputString As String

    outputString = inString
    outputString = Replace(outputString, "*1mm", "")
    outputString = Replace(outputString, "*1deg", "")
    outputString = Replace(outputString, "mm", "")
    outputString = Replace(outputString, "deg", "")

    ' Return statement
    RemoveUnits = outputString

End Function

Public Function MultiplyByTwo(inString As String) As String

    ' Return object
    Dim outputString As String
    
    outputString = inString
    outputString = "(" + outputString + ")*2"
    
    ' Return statement
    MultiplyByTwo = outputString
    
End Function

Public Function DivideByTwo(inString As String) As String

    ' Return object
    Dim outputString As String
    
    outputString = inString
    outputString = "(" + outputString + ")/2"
    
    ' Return statement
    DivideByTwo = outputString

End Function

Public Function ProcessFormula(inString As String) As String

    ' Return object
    Dim outputString As String
    
    outputString = inString
    outputString = parseformula(outputString, False, False)

    ' Return statement
    ProcessFormula = outputString
    
End Function

' Taken from the old CATIA2GDML converter
Private Function parseformula(formula As String, isArcFunc As Boolean, isTrigFunc As Boolean) As String
    
    Dim pieces As New Collection
    Dim piece As String

    Dim opBrPos As Integer
    Dim clBrPos As Integer
    
    Dim cursor As Integer
    Dim opBrCounter As Integer
    Dim clBrCounter As Integer
    
    cursor = 1
    opBrPos = InStr(cursor, formula, "(")           ' Try to find as opening bracket
    
    If (opBrPos <> 0) Then                          ' If the opening bracket found
        piece = Left(formula, opBrPos - 1)          ' then save everything that was before it
        pieces.Add piece
    Else
        parseformula = formula                      ' If no opening bracket found
        'ListBox2.AddItem formula                    ' return the input string
        'ListBox2.AddItem "--------------------------------------------------------------------"
        Exit Function
    End If

    ' Loop through all the pairs of brackets
    Do While (opBrPos <> 0)
    
        ' Find corresponding closing bracket
        cursor = opBrPos
        opBrCounter = 1
        clBrCounter = 0
        Do While (opBrCounter - clBrCounter > 0)
            cursor = cursor + 1
            If (Mid(formula, cursor, 1) = ")") Then
                clBrCounter = clBrCounter + 1
            ElseIf (Mid(formula, cursor, 1) = "(") Then
                opBrCounter = opBrCounter + 1
            End If
            
            ' error case - incorrect number of brackets
            ' not implemented - hope CATIA controles this :-)
        Loop
        clBrPos = cursor

        ' Store the string that was inside these brackets
        Dim inhalt As String
        inhalt = Mid(formula, opBrPos + 1, clBrPos - opBrPos - 1)

        ' Check if the brackets correspond to the trigonometric function
        Dim inhaltArc As Boolean        ' sin, cos, tan
        Dim inhaltTrig As Boolean       ' asin, acis, atan
        inhaltArc = False
        inhaltTrig = False

        Dim inhaltReturn As String
        Dim prefix As String
        Dim preprefix As String
        If (opBrPos - 3 >= 1) Then
            prefix = Mid(formula, opBrPos - 3, 3)
            If (prefix = "sin" Or prefix = "cos" Or prefix = "tan") Then
                inhaltArc = False
                inhaltTrig = True
                If (opBrPos - 4 >= 1) Then
                    preprefix = Mid(formula, opBrPos - 4, 1)
                    If (preprefix = "a") Then
                        inhaltArc = True
                        inhaltTrig = False
                    End If
                End If
            End If
        End If

        ' Parse the string that was in the brackets
        inhaltReturn = parseformula(inhalt, inhaltArc, inhaltTrig)

        ' Store the result of parsing the inner string

        If (inhaltArc = True) Then
            pieces.Add "(" + inhaltReturn + ")/DEGtoRAD"
            'ListBox1.AddItem "((" + inhaltReturn + ")/DEGtoRAD)"
        ElseIf (inhaltTrig = True) Then
            pieces.Add "((" + inhaltReturn + ")*DEGtoRAD)"
            'ListBox1.AddItem "((" + inhaltReturn + ")*DEGtoRAD)"
        Else
            pieces.Add "(" + inhaltReturn + ")"
            'ListBox1.AddItem "(" + inhaltReturn + ")"
        End If

        ' "goto" the next pair of brackets
        opBrPos = InStr(cursor, formula, "(")

        If (opBrPos = 0) Then                       ' if no more - store the rest of the line
            pieces.Add Mid(formula, clBrPos + 1)
        Else                                        ' if there is one - store the string between the closing and opening brackets
            pieces.Add Mid(formula, clBrPos + 1, opBrPos - clBrPos - 1)
        End If

    Loop

    ' Glue the pieces and return the result up the recursive tree
    Dim retStr As String
    retStr = ""
    Dim i As Integer
    For i = 1 To pieces.Count
        'ListBox2.AddItem pieces.Item(i)
        retStr = retStr + pieces.Item(i)
    Next i
    'ListBox2.AddItem "--------------------------------------------------------------------"

    parseformula = retStr

End Function

' A method which checks whether some key is in the collection or not
Public Function MyContains(col As Collection, key As Variant) As Boolean

    Dim obj As Variant

On Error GoTo err

    MyContains = True
    obj = col(key)
    Exit Function

err:
    MyContains = False

End Function

Attribute VB_Name = "cls_PosRot"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' Related to rotation
Private fRotZYXangle(2) As Double
Private fRotZYXwithRelation(2) As Boolean
Private fRotZYXformula(2) As String

' Related to translation
Private fPosXYZcoord(2) As Double
Private fPosXYZwithRelation(2) As Boolean
Private fPosXYZformula(2) As String

Private Sub Class_Initialize()
    fRotZYXangle(0) = 0#
    fRotZYXangle(1) = 0#
    fRotZYXangle(2) = 0#
    fRotZYXwithRelation(0) = False
    fRotZYXwithRelation(1) = False
    fRotZYXwithRelation(2) = False
    fPosXYZcoord(0) = 0#
    fPosXYZcoord(1) = 0#
    fPosXYZcoord(2) = 0#
    fPosXYZwithRelation(0) = False
    fPosXYZwithRelation(1) = False
    fPosXYZwithRelation(2) = False
End Sub

Public Property Get rotZYXangle(i As Integer) As Double
    rotZYXangle = fRotZYXangle(i)
End Property

Public Property Get rotZYXwithRelation(i As Integer) As Boolean
    rotZYXwithRelation = fRotZYXwithRelation(i)
End Property

Public Property Get rotZYXformula(i As Integer) As String
    rotZYXformula = fRotZYXformula(i)
End Property

Public Property Get posXYZcoord(i As Integer) As Double
    posXYZcoord = fPosXYZcoord(i)
End Property

Public Property Get posXYZwithRelation(i As Integer) As Boolean
    posXYZwithRelation = fPosXYZwithRelation(i)
End Property

Public Property Get posXYZformula(i As Integer) As String
    posXYZformula = fPosXYZformula(i)
End Property

Public Sub ProcessRotateFeature(rotateFeature As Rotate)

    Dim rotRelation As Relation
    
    If (LCase(Left(rotateFeature.Name, 8)) = "rotate.z") Then
        If (rotateFeature.Angle.OptionalRelation Is Nothing) Then
            fRotZYXangle(0) = rotateFeature.AngleValue * 180# / PI
            formCATIA2GDML.ListBox1.AddItem "Rotate.Z = " + Trim(Str(rotZYXangle(0)))
        Else
            Set rotRelation = rotateFeature.Angle.OptionalRelation
            fRotZYXformula(0) = rotRelation.Value
            formCATIA2GDML.ListBox1.AddItem "Rotate.Z = " + rotZYXformula(0)
            fRotZYXwithRelation(0) = True
        End If

    ElseIf (LCase(Left(rotateFeature.Name, 8)) = "rotate.y") Then
        If (rotateFeature.Angle.OptionalRelation Is Nothing) Then
            fRotZYXangle(1) = rotateFeature.AngleValue * 180# / PI
            formCATIA2GDML.ListBox1.AddItem "Rotate.Y = " + Trim(Str(rotZYXangle(1)))
        Else
            Set rotRelation = rotateFeature.Angle.OptionalRelation
            fRotZYXformula(1) = rotRelation.Value
            formCATIA2GDML.ListBox1.AddItem "Rotate.Y = " + rotZYXformula(1)
            fRotZYXwithRelation(1) = True
        End If

    ElseIf (LCase(Left(rotateFeature.Name, 8)) = "rotate.x") Then
        If (rotateFeature.Angle.OptionalRelation Is Nothing) Then
            fRotZYXangle(2) = rotateFeature.AngleValue * 180# / PI
            formCATIA2GDML.ListBox1.AddItem "Rotate.X = " + Trim(Str(rotZYXangle(2)))
        Else
            Set rotRelation = rotateFeature.Angle.OptionalRelation
            fRotZYXformula(2) = rotRelation.Value
            formCATIA2GDML.ListBox1.AddItem "Rotate.X = " + rotZYXformula(2)
            fRotZYXwithRelation(2) = True
        End If
    End If

End Sub

Public Sub ProcessTranslateFeature(transFeature As HybridShape, prt As Part)

    Dim posRelation As Relation

    Dim prtParamsSubset As Parameters
    Dim searchedParamNames(5) As String
    Set prtParamsSubset = prt.Parameters.SubList(transFeature, True)
    searchedParamNames(0) = transFeature.Name + "\CoordX"
    searchedParamNames(1) = transFeature.Name + "\CoordY"
    searchedParamNames(2) = transFeature.Name + "\CoordZ"
    searchedParamNames(3) = transFeature.Name + "\X"            'TODO - make all translations with Coord*. Check Inserter macro.
    searchedParamNames(4) = transFeature.Name + "\Y"
    searchedParamNames(5) = transFeature.Name + "\Z"
    Dim nFound As Integer
    nFound = 0
    
    Dim curParam As Parameter
    Dim iParam As Integer
    For iParam = 1 To prtParamsSubset.Count
        If (InStr(1, prtParamsSubset.Item(iParam).Name, searchedParamNames(0)) Or _
            InStr(1, prtParamsSubset.Item(iParam).Name, searchedParamNames(3))) Then
            nFound = nFound + 1
            Set curParam = prtParamsSubset.Item(iParam)
            If (curParam.OptionalRelation Is Nothing) Then
                fPosXYZcoord(0) = transFeature.CoordXValue * 1000#
                formCATIA2GDML.ListBox1.AddItem "Trans.X = " + Trim(Str(posXYZcoord(0)))
            Else
                Set posRelation = curParam.OptionalRelation
                fPosXYZformula(0) = posRelation.Value
                formCATIA2GDML.ListBox1.AddItem "Trans.X = " + posXYZformula(0)
                fPosXYZwithRelation(0) = True
            End If
        ElseIf (InStr(1, prtParamsSubset.Item(iParam).Name, searchedParamNames(1)) Or _
                InStr(1, prtParamsSubset.Item(iParam).Name, searchedParamNames(4))) Then
            nFound = nFound + 1
            Set curParam = prtParamsSubset.Item(iParam)
            If (curParam.OptionalRelation Is Nothing) Then
                fPosXYZcoord(1) = transFeature.CoordYValue * 1000#
                formCATIA2GDML.ListBox1.AddItem "Trans.Y = " + Trim(Str(posXYZcoord(1)))
            Else
                Set posRelation = curParam.OptionalRelation
                fPosXYZformula(1) = posRelation.Value
                formCATIA2GDML.ListBox1.AddItem "Trans.Y = " + posXYZformula(1)
                fPosXYZwithRelation(1) = True
            End If
        ElseIf (InStr(1, prtParamsSubset.Item(iParam).Name, searchedParamNames(2)) Or _
                InStr(1, prtParamsSubset.Item(iParam).Name, searchedParamNames(5))) Then
            nFound = nFound + 1
            Set curParam = prtParamsSubset.Item(iParam)
            If (curParam.OptionalRelation Is Nothing) Then
                fPosXYZcoord(2) = transFeature.CoordZValue * 1000#
                formCATIA2GDML.ListBox1.AddItem "Trans.Z = " + Trim(Str(posXYZcoord(2)))
            Else
                Set posRelation = curParam.OptionalRelation
                fPosXYZformula(2) = posRelation.Value
                formCATIA2GDML.ListBox1.AddItem "Trans.Z = " + posXYZformula(2)
                fPosXYZwithRelation(2) = True
            End If
        End If
    Next iParam
    
    If (nFound > 3) Then
        ' error
    End If

End Sub

Attribute VB_Name = "formCATIA2GDML"
Attribute VB_Base = "0{5B5DBFC1-66EC-44B1-A52C-A73EDF14414C}{2ADA134A-9188-4C38-8E3F-E239B451D5CD}"
Attribute VB_GlobalNameSpace = False
Attribute VB_Creatable = False
Attribute VB_PredeclaredId = True
Attribute VB_Exposed = False
Attribute VB_TemplateDerived = False
Attribute VB_Customizable = False
Option Explicit

Private Sub ComboBox2_Change()

    Dim docs As Documents
    Set docs = CATIA.Documents

    Dim MCprod As ProductDocument

    Dim iDoc As Integer
    For iDoc = 1 To docs.Count

        If (docs.Item(iDoc).Name = formCATIA2GDML.ComboBox2.Text) Then
            Set MCprod = docs.Item(iDoc)
        End If

    Next iDoc

    ' =====================================================

    Dim prods As Products
    Set prods = MCprod.Product.Products

    ' First clear the combobox
    formCATIA2GDML.ComboBox1.Clear

    ' Loop over the components of the top product to fill the combobox
    Dim iProd As Integer
    For iProd = prods.Count To 1 Step -1
        Dim prod As Product
        'Dim prodInstanceName As String
        Dim prodPartNumber As String
        'Dim prodFilename As String
        'Dim prtDoc As PartDocument
        'Dim prt As Part
        'Dim prtProd As Product

        Set prod = prods.Item(iProd)
        'prodInstanceName = prod.name
        prodPartNumber = prod.PartNumber
        'prodFilename = prod.ReferenceProduct.Parent.name
        'Set prtDoc = prod.ReferenceProduct.Parent
        'Set prt = prtDoc.Part
        'Set prtProd = prtDoc.Product

        formCATIA2GDML.ComboBox1.AddItem prodPartNumber

    Next iProd

    ' Automatically select the last volume as the top volume
    If (formCATIA2GDML.ComboBox1.ListCount > 0) Then
        formCATIA2GDML.ComboBox1.ListIndex = 0
        formCATIA2GDML.CommandButton1.Enabled = True
    End If

End Sub

Private Sub CommandButton1_Click()

    formCATIA2GDML.CommandButton1.Enabled = False

    Dim docs As Documents
    Set docs = CATIA.Documents

    Dim MCprod As ProductDocument

    Dim i As Integer
    For i = 1 To docs.Count

        If (docs.Item(i).Name = formCATIA2GDML.ComboBox2.Text) Then
            Set MCprod = docs.Item(i)
        End If

    Next i

    ' =====================================================

    Call InitGDML(formCATIA2GDML.ComboBox1.Text)
    Call PrepareDefineAndMaterialsSection(CATIA.ActiveDocument) 'Patch for RICH optimization model

    Call LoopOverProduct(MCprod)

    ' Temporary file
    Dim tmpFilename As String
    tmpFilename = Environ("Temp") + "/CATIA2GDML.tmp.gdml"

    ' First write output GDML into a temporary file
    Dim outputFilename As String
    outputFilename = txtFilename.Text

    If (outputFilename <> "") Then
        GDMLfile.Save tmpFilename
        ' Then postprocess temporary file and write result into the final output file
        Call Postprocess(tmpFilename, outputFilename)
        MsgBox "Done!"
    Else
        err.Raise vbObjectError + 513, "", "Empty output file name."
    End If

End Sub

Private Sub CommandButton2_Click()

    End

End Sub

Private Sub CommandButton3_Click()

'On Error GoTo cancelHandler

    Dim filter As String
    Dim obtainedFilename As String
    filter = "GDML files (*.gdml)|*.gdml|All files (*.*)|*.*"
    
#If VBA7 Then

    obtainedFilename = DialogsVB7.FileBrowseSave("", "", "Save file", filter, 0)

#Else

    Dim cdFolderPath As New CommonDialog

    cdFolderPath.filter = filter
    cdFolderPath.ShowSave
    
    obtainedFilename = cdFolderPath.filename

    If (obtainedFilename = "") Then GoTo cancelHandler

#End If
        
    txtFilename.Text = obtainedFilename

cancelHandler:
    ' Cancel button pressed

End Sub

Private Sub UserForm_Initialize()

    ' TODO
    formCATIA2GDML.txtFilename.Text = "C:\CATIA-GDML_geometry_builder\05_Examples\Xtru_test\Xtru_test.gdml"

    ' List all CATProduct documents in the first combobox
    Dim docs As Documents
    Set docs = CATIA.Documents

    Dim iDoc As Integer
    For iDoc = 1 To docs.Count
        If (TypeName(docs.Item(iDoc)) = "ProductDocument") Then
            formCATIA2GDML.ComboBox2.AddItem docs.Item(iDoc).Name
        End If
    Next iDoc

End Sub

Private Sub ComboBox1_Change()

    If (formCATIA2GDML.ComboBox1.Text <> "") Then
        formCATIA2GDML.CommandButton1.Enabled = True
    Else
        formCATIA2GDML.CommandButton1.Enabled = False
    End If

End Sub
