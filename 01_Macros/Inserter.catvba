Attribute VB_Name = "CommonDigitalString"
Option Explicit

Public Function isNum(str As String) As Boolean

    Dim i As Integer
    Dim flag As Boolean
    flag = False
    isNum = True
    For i = 1 To Len(str)
        If isDigit(Mid(str, i, 1)) = False Then
            isNum = False
        End If
    Next

End Function

Public Function isDigit(str As String) As Boolean

    Dim arr(0 To 9) As String
    Dim i As Integer
    arr(0) = "0"
    arr(1) = "1"
    arr(2) = "2"
    arr(3) = "3"
    arr(4) = "4"
    arr(5) = "5"
    arr(6) = "6"
    arr(7) = "7"
    arr(8) = "8"
    arr(9) = "9"
    isDigit = False
    For i = 0 To 9
        If str = arr(i) Then
            isDigit = True
        End If
    Next

End Function

Attribute VB_Name = "Inserter"
Sub CATMain()

    formInserter.Show

End Sub

Attribute VB_Name = "Support"
Option Explicit

''''''' to fit line-to-line with Replica code '''''''
''''''' to fit line-to-line with Replica code '''''''

Public Sub coincidence_std_planes()

    Dim ProductDoc As ProductDocument
    Set ProductDoc = CATIA.ActiveDocument
    
    Dim Product1 As Product
    Dim Product2 As Product
    
    Dim reference1 As Reference
    Dim reference2 As Reference
    
    Dim str1 As String
    Dim str2 As String
    Dim str3 As String
    Dim str4 As String
    Dim flag As Boolean
    
    Dim ConstraintsCollection As Constraints
    Set ConstraintsCollection = ProductDoc.Product.Connections("CATIAConstraints")
    
    Dim myConstraint As Constraint
    Dim i As Integer
    
    For i = 1 To ProductDoc.Product.Products.Count
        If (ProductDoc.Product.Products.Item(i).PartNumber = formInserter.PhysicalPartComboBox.Text) Then
            Set Product1 = ProductDoc.Product.Products.Item(i)
        End If
        If (ProductDoc.Product.Products.Item(i).PartNumber = formInserter.LogicalPartComboBox.Text) Then
            Set Product2 = ProductDoc.Product.Products.Item(i)
        End If
    Next i
    
    'xy planes processing
    flag = False
    str1 = ProductDoc.Product.Name + "/" + Product1.Name + "/!xy plane"
    str2 = ProductDoc.Product.Name + "/" + Product2.Name + "/!xy plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If
    
    'yz planes processing
    flag = False
    str1 = ProductDoc.Product.Name + "/" + Product1.Name + "/!yz plane"
    str2 = ProductDoc.Product.Name + "/" + Product2.Name + "/!yz plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If
    
    'zx planes processing
    flag = False
    str1 = ProductDoc.Product.Name + "/" + Product1.Name + "/!zx plane"
    str2 = ProductDoc.Product.Name + "/" + Product2.Name + "/!zx plane"

    For i = 1 To ConstraintsCollection.Count
        If (ConstraintsCollection.Item(i).Type = catCstTypeOn) Then
            str3 = ConstraintsCollection.Item(i).GetConstraintElement(1).DisplayName
            str4 = ConstraintsCollection.Item(i).GetConstraintElement(2).DisplayName
            If ((str1 = str3 And str2 = str4) Or (str1 = str4 And str2 = str3)) Then
                flag = True
                Exit For
            End If
        End If
    Next i

    If (Not flag) Then
        Set reference1 = ProductDoc.Product.CreateReferenceFromName(str1)
        Set reference2 = ProductDoc.Product.CreateReferenceFromName(str2)
        Set myConstraint = ConstraintsCollection.AddBiEltCst(catCstTypeOn, reference1, reference2)
        myConstraint.Orientation = catCstOrientSame
    End If

End Sub

Public Sub generateTransformations(partDoc As PartDocument)

    Dim hybShpFactory As HybridShapeFactory
    Dim shpFactory As ShapeFactory
    Dim origin As OriginElements
    Dim refPlaneXY As Reference
    Dim refPlaneYZ As Reference
    Dim refPlaneZX As Reference
    Dim sel As Selection
    Dim visPropSet As VisPropertySet
    
    Set hybShpFactory = partDoc.Part.HybridShapeFactory
    Set shpFactory = partDoc.Part.ShapeFactory
    Set origin = partDoc.Part.OriginElements
    Set refPlaneXY = partDoc.Part.CreateReferenceFromObject(origin.PlaneXY)
    Set refPlaneYZ = partDoc.Part.CreateReferenceFromObject(origin.PlaneYZ)
    Set refPlaneZX = partDoc.Part.CreateReferenceFromObject(origin.PlaneZX)
    Set sel = CATIA.ActiveDocument.Selection
    Set visPropSet = sel.VisProperties
    
    Dim Intersection_XY_ZX As HybridShapeIntersection
    Dim Intersection_YZ_XY As HybridShapeIntersection
    Dim Intersection_ZX_YZ As HybridShapeIntersection

    'Z axis preparation
    Set Intersection_ZX_YZ = hybShpFactory.AddNewIntersection(refPlaneZX, refPlaneYZ)
    Intersection_ZX_YZ.PointType = 0
    partDoc.Part.Bodies.Item(partDoc.Part.Bodies.Count).InsertHybridShape Intersection_ZX_YZ
'    partDoc.Part.InWorkObject = Intersection_ZX_YZ
    Intersection_ZX_YZ.Name = "Z axis"
    sel.Clear
    sel.Add Intersection_ZX_YZ
    visPropSet.SetShow catVisPropertyNoShowAttr
    sel.Clear
'    partDoc.Part.Update
    'Y axis preparation
    Set Intersection_YZ_XY = hybShpFactory.AddNewIntersection(refPlaneYZ, refPlaneXY)
    Intersection_YZ_XY.PointType = 0
    partDoc.Part.Bodies.Item(partDoc.Part.Bodies.Count).InsertHybridShape Intersection_YZ_XY
'    partDoc.Part.InWorkObject = Intersection_YZ_XY
    Intersection_YZ_XY.Name = "Y axis"
    sel.Clear
    sel.Add Intersection_YZ_XY
    visPropSet.SetShow catVisPropertyNoShowAttr
    sel.Clear
'    partDoc.Part.Update
    'X axis preparation
    Set Intersection_XY_ZX = hybShpFactory.AddNewIntersection(refPlaneXY, refPlaneZX)
    Intersection_XY_ZX.PointType = 0
    partDoc.Part.Bodies.Item(partDoc.Part.Bodies.Count).InsertHybridShape Intersection_XY_ZX
'    partDoc.Part.InWorkObject = Intersection_XY_ZX
    Intersection_XY_ZX.Name = "X axis"
    sel.Clear
    sel.Add Intersection_XY_ZX
    visPropSet.SetShow catVisPropertyNoShowAttr
    sel.Clear
'    partDoc.Part.Update

    Dim refAxisX As Reference
    Dim refAxisY As Reference
    Dim refAxisZ As Reference
    Dim hybShpRotX As HybridShapeRotate
    Dim hybShpRotY As HybridShapeRotate
    Dim hybShpRotZ As HybridShapeRotate
    Dim hybShpTrans As HybridShapeTranslate
    Dim rotX As Rotate
    Dim rotY As Rotate
    Dim rotZ As Rotate
    Dim trans As Translate

    'Rotate by Z axis creation
    Set refAxisZ = partDoc.Part.CreateReferenceFromObject(Intersection_ZX_YZ)
    Set rotZ = shpFactory.AddNewRotate2(refAxisZ, 0)
    Set hybShpRotZ = rotZ.HybridShape
    hybShpRotZ.RotationType = 0
    hybShpRotZ.Axis = refAxisZ
    hybShpRotZ.Name = "Rotate.Z"
'    partDoc.Part.InWorkObject = hybShpRotZ
'    partDoc.Part.Update
    'Rotate by Y axis creation
    Set refAxisY = partDoc.Part.CreateReferenceFromObject(Intersection_YZ_XY)
    Set rotY = shpFactory.AddNewRotate2(refAxisY, 0)
    Set hybShpRotY = rotY.HybridShape
    hybShpRotY.RotationType = 0
    hybShpRotY.Axis = refAxisY
    hybShpRotY.Name = "Rotate.Y"
'    partDoc.Part.InWorkObject = hybShpRotY
'    partDoc.Part.Update
    'Rotate by X axis creation
    Set refAxisX = partDoc.Part.CreateReferenceFromObject(Intersection_XY_ZX)
    Set rotX = shpFactory.AddNewRotate2(refAxisX, 0)
    Set hybShpRotX = rotX.HybridShape
    hybShpRotX.RotationType = 0
    hybShpRotX.Axis = refAxisX
    hybShpRotX.Name = "Rotate.X"
'    partDoc.Part.InWorkObject = hybShpRotX
'    partDoc.Part.Update
    
    'Translation
    Set trans = shpFactory.AddNewTranslate2(0)
    Set hybShpTrans = trans.HybridShape
    hybShpTrans.VectorType = 2
    
#If VBA7 Then
    
    hybShpTrans.CoordXValue = Val(formInserter.txtX.Text)
    hybShpTrans.CoordYValue = Val(formInserter.txtY.Text)
    hybShpTrans.CoordZValue = Val(formInserter.txtZ.Text)
'    partDoc.Part.InWorkObject = hybShpTrans

#Else
    
    hybShpTrans.CoordXValue = Val(formInserter.txtX.Text) / 1000#
    hybShpTrans.CoordYValue = Val(formInserter.txtY.Text) / 1000#
    hybShpTrans.CoordZValue = Val(formInserter.txtZ.Text) / 1000#
'    partDoc.Part.InWorkObject = hybShpTrans

#End If

    ' Update
'    partDoc.Part.Update

End Sub

Attribute VB_Name = "formInserter"
Attribute VB_Base = "0{F48A128E-974F-4206-ADA3-41C8CCC0E873}{2FCBECA6-B357-4978-AF97-59BF1139BC72}"
Attribute VB_GlobalNameSpace = False
Attribute VB_Creatable = False
Attribute VB_PredeclaredId = True
Attribute VB_Exposed = False
Attribute VB_TemplateDerived = False
Attribute VB_Customizable = False
Option Explicit

Dim PartVolumePair As Collection
' Key - part number ("G4_World"), item - pointer to the document ("G4_World.CATPart")

Private Sub LogicalPartComboBox_Change()
    If (PhysicalPartComboBox.Text <> "") And (LogicalPartComboBox.Text <> "") Then
        Call nameGenerate
    End If
End Sub

Private Sub PhysicalPartComboBox_Change()
    If (PhysicalPartComboBox.Text <> "") And (LogicalPartComboBox.Text <> "") Then
        Call nameGenerate
    End If
End Sub

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument
    
    ' Translate to design mode
'    MsgBox "Parts in this product are to be translated into 'Design Mode'" + vbNewLine + "This may take a few minutes, please wait.", vbExclamation, "Translate to Design mode"
'    prodDoc.Product.ApplyWorkMode DESIGN_MODE

    Dim subprods As Products
    Set subprods = prodDoc.Product.Products
    Set PartVolumePair = New Collection

    Dim i As Integer
    Dim partBodyPubl As Publication
    For i = 1 To subprods.Count

        On Error GoTo NoPartBody
        Set partBodyPubl = subprods.Item(i).Publications.Item("PartBody")
        PhysicalPartComboBox.AddItem subprods.Item(i).PartNumber
NoPartBody:
        On Error GoTo 0

        LogicalPartComboBox.AddItem subprods.Item(i).PartNumber
        PartVolumePair.Add subprods.Item(i).ReferenceProduct.Parent, subprods.Item(i).PartNumber
    Next i

    ' Init translation with 0
    txtX.Text = "0"
    txtY.Text = "0"
    txtZ.Text = "0"

    cmbInsert.Enabled = False

End Sub

Private Sub cmbInsert_Click()

    ' GUI
    lblStatus.Caption = "Inserting. Please, wait."

    ' Do "coincidence standard planes" if switched on
    If chkCSP.Value = True Then Call coincidence_std_planes

    Dim ProductDoc As ProductDocument
    Set ProductDoc = CATIA.ActiveDocument

    ' Find the publication to be copied
    Dim pub As Publication
    Dim i As Integer
    For i = 1 To ProductDoc.Product.Products.Count
        If (ProductDoc.Product.Products.Item(i).PartNumber = PhysicalPartComboBox.Text) Then
            Set pub = ProductDoc.Product.Products.Item(i).Publications.Item("PartBody")
            Exit For
        End If
    Next i

    Dim partDoc As PartDocument
    Set partDoc = PartVolumePair.Item(LogicalPartComboBox.Text)

    ' Copy - paste - as result with link
    Dim sel As Selection
    Set sel = CATIA.ActiveDocument.Selection
    sel.Clear
    sel.Add pub
    sel.Copy
    sel.Clear
    sel.Add partDoc.Part
    sel.PasteSpecial "CATPrtResult"
    sel.Clear
    
    ' Rename recent copied body
    partDoc.Part.Bodies.Item(partDoc.Part.Bodies.Count).Name = txtGenName.Text
    ' Generate empty transformations
    generateTransformations partDoc
    ''''''' to fit line-to-line with ArrayMaker code '''''''
    ''''''' to fit line-to-line with ArrayMaker code '''''''

    ' Changing the shape of the mother volume if the mother volume is assembly-volume
    If (ChBoxAssembly.Value) Then

        sel.Add partDoc.Part.Bodies.Item(partDoc.Part.Bodies.Count)
        sel.Copy
        sel.PasteSpecial "CATPrtResult"
        sel.Clear
        
        Dim shpFac As ShapeFactory
        Set shpFac = partDoc.Part.ShapeFactory
        partDoc.Part.InWorkObject = partDoc.Part.Bodies.Item("PartBody")
        Dim add1 As Add
        Set add1 = shpFac.AddNewAdd(partDoc.Part.Bodies.Item(partDoc.Part.Bodies.Count))
        add1.Name = "Assembly_part." + Trim(str(partDoc.Part.Bodies.Item("PartBody").Shapes.Count))
        
        ' Parameter Material=Assembly
        For i = 1 To partDoc.Part.Parameters.Count
            If InStr(1, partDoc.Part.Parameters.Item(i).Name, "Material") > 0 Then
                partDoc.Part.Parameters.Item(i).ValuateFromString "Assembly"
            End If
        Next i

    End If

    ' Update
    partDoc.Part.Update

    Call nameGenerate

    ' GUI
    lblStatus.Caption = "Inserted." + vbNewLine + "Press 'Exit' to finish or fill all the fields and press 'Create' button."

End Sub

Private Sub nameGenerate()

    If (PhysicalPartComboBox.Text = LogicalPartComboBox.Text) Then
        MsgBox "You have selected the same part twice.", vbExclamation, "Attention"
        txtGenName.Text = ""
        cmbInsert.Enabled = False
        Exit Sub
    End If
    
    Dim ProductDoc As ProductDocument
    Dim partDoc As PartDocument
    Set ProductDoc = CATIA.ActiveDocument
    Set partDoc = PartVolumePair.Item(LogicalPartComboBox.Text)

    Dim i As Integer
    Dim maxIndex As Integer
    Dim prefixLine As String
    Dim indexLine As String
    maxIndex = 0
    prefixLine = "Body." + PhysicalPartComboBox.Text + "."
    For i = 1 To partDoc.Part.Bodies.Count
        If (StrComp(Mid(partDoc.Part.Bodies.Item(i).Name, 1, Len(prefixLine)), prefixLine, vbTextCompare) = 0) Then
            indexLine = Mid(partDoc.Part.Bodies.Item(i).Name, Len(prefixLine) + 1)
            If ((CommonDigitalString.isNum(indexLine) = True) And (Val(indexLine) > maxIndex)) Then
                maxIndex = Val(indexLine)
            End If
        End If
    Next

    txtGenName.Text = prefixLine & (maxIndex + 1)
    cmbInsert.Enabled = True

End Sub

Private Sub cmbCancel_Click()

    End

End Sub
