Attribute VB_Name = "Matrix"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' Matrix class

Option Explicit

Const PI = 3.14159265358979

' first index - row index
' second index - column index

' -- Data members ----------------------------------------------------------------------

Private mDimension As Integer       ' This number is one less than the size of the matrix
Private mData() As Double

Dim mAlpha As Double
Dim mBeta As Double
Dim mGamma As Double

' -- Methods ---------------------------------------------------------------------------

' OK
Public Sub SetDimension(p_dimension As Integer)
    mDimension = p_dimension - 1
    ReDim mData(0 To mDimension, 0 To mDimension) As Double
End Sub

' OK
Public Sub SetData(p_inData() As Double)
    Dim i As Integer, j As Integer
    For i = 0 To mDimension
        For j = 0 To mDimension
            mData(i, j) = p_inData(i, j)
        Next j
    Next i
End Sub

' OK
Public Sub GetData(o_outData() As Double)
    Dim i As Integer, j As Integer
    For i = 0 To mDimension
        For j = 0 To mDimension
            o_outData(i, j) = mData(i, j)
        Next j
    Next i
End Sub

Public Sub Draw()
    Dim i As Integer, j As Integer
    Dim v_str As String
    v_str = ""
    For i = 0 To mDimension
        For j = 0 To mDimension
            v_str = v_str & mData(i, j) & " "
        Next j
        v_str = v_str & vbNewLine
    Next i
    MsgBox v_str
End Sub

' OK
Public Sub EvaluateIdentity()
    Dim i As Integer, j As Integer
    For i = 0 To mDimension
        For j = 0 To mDimension
            If (i = j) Then
                mData(i, j) = 1#
            Else
                mData(i, j) = 0#
            End If
        Next j
    Next i
End Sub

' OK
Public Sub Evaluate4x4(p_a11 As Double, p_a12 As Double, p_a13 As Double, p_a14 As Double, _
                p_a21 As Double, p_a22 As Double, p_a23 As Double, p_a24 As Double, _
                p_a31 As Double, p_a32 As Double, p_a33 As Double, p_a34 As Double, _
                p_a41 As Double, p_a42 As Double, p_a43 As Double, p_a44 As Double)
    mData(0, 0) = p_a11
    mData(0, 1) = p_a12
    mData(0, 2) = p_a13
    mData(0, 3) = p_a14
    mData(1, 0) = p_a21
    mData(1, 1) = p_a22
    mData(1, 2) = p_a23
    mData(1, 3) = p_a24
    mData(2, 0) = p_a31
    mData(2, 1) = p_a32
    mData(2, 2) = p_a33
    mData(2, 3) = p_a34
    mData(3, 0) = p_a41
    mData(3, 1) = p_a42
    mData(3, 2) = p_a43
    mData(3, 3) = p_a44
End Sub

' OK
Public Sub Multiply(p_operand2 As Matrix)
    Dim v_operand2_arr() As Double
    ReDim v_operand2_arr(0 To mDimension, 0 To mDimension) As Double
    p_operand2.GetData v_operand2_arr
    Me.Multiply2 v_operand2_arr
End Sub

' OK
Public Sub Multiply2(p_operand2() As Double)
    Dim Ai As Integer, Bi As Integer, Bj As Integer
    Dim v_temp() As Double
    ReDim v_temp(0 To mDimension, 0 To mDimension) As Double

    For Ai = 0 To mDimension
        For Bj = 0 To mDimension
            For Bi = 0 To mDimension
                v_temp(Ai, Bj) = v_temp(Ai, Bj) + mData(Ai, Bi) * p_operand2(Bi, Bj)
            Next Bi
        Next Bj
    Next Ai

    Me.SetData v_temp
End Sub

' OK
Public Sub MultiplyXrot(p_alphaInRads As Double)
    Dim v_mat As New Matrix
    v_mat.SetDimension 4
    v_mat.Evaluate4x4 1#, 0#, 0#, 0#, _
            0#, Cos(p_alphaInRads), -Sin(p_alphaInRads), 0#, _
            0#, Sin(p_alphaInRads), Cos(p_alphaInRads), 0#, _
            0#, 0#, 0#, 1#
    Me.Multiply v_mat
End Sub

' OK
Public Sub MultiplyYrot(p_alphaInRads As Double)
    Dim v_mat As New Matrix
    v_mat.SetDimension 4
    v_mat.Evaluate4x4 Cos(p_alphaInRads), 0#, Sin(p_alphaInRads), 0#, _
            0#, 1#, 0#, 0#, _
            -Sin(p_alphaInRads), 0#, Cos(p_alphaInRads), 0#, _
            0#, 0#, 0#, 1#
    Me.Multiply v_mat
End Sub

' OK
Public Sub MultiplyZrot(p_alphaInRads As Double)
    Dim v_mat As New Matrix
    v_mat.SetDimension 4
    v_mat.Evaluate4x4 Cos(p_alphaInRads), -Sin(p_alphaInRads), 0#, 0#, _
            Sin(p_alphaInRads), Cos(p_alphaInRads), 0#, 0#, _
            0#, 0#, 1#, 0#, _
            0#, 0#, 0#, 1#
    Me.Multiply v_mat
End Sub

' OK
Public Sub MultiplyXYZposRow(p_posX As Double, p_posY As Double, p_posZ As Double)
    Dim v_mat As New Matrix
    v_mat.SetDimension 4
    v_mat.Evaluate4x4 1#, 0#, 0#, 0#, _
            0#, 1#, 0#, 0#, _
            0#, 0#, 1#, 0#, _
            p_posX, p_posY, p_posZ, 1#
    Me.Multiply v_mat
End Sub

' OK
Public Sub MultiplyXYZposCol(p_posX As Double, p_posY As Double, p_posZ As Double)
    Dim v_mat As New Matrix
    v_mat.SetDimension 4
    v_mat.Evaluate4x4 1#, 0#, 0#, p_posX, _
            0#, 1#, 0#, p_posY, _
            0#, 0#, 1#, p_posZ, _
            0, 0, 0, 1#
    Me.Multiply v_mat
End Sub

' OK
Public Function GetXposfromTXYZ()
    GetXposfromTXYZ = mData(0, 3)
End Function
Public Function GetYposfromTXYZ()
    GetYposfromTXYZ = mData(1, 3)
End Function
Public Function GetZposfromTXYZ()
    GetZposfromTXYZ = mData(2, 3)
End Function

' OK
Public Function GetXposfromZYXT()
    GetXposfromZYXT = mData(3, 0)
End Function
Public Function GetYposfromZYXT()
    GetYposfromZYXT = mData(3, 1)
End Function
Public Function GetZposfromZYXT()
    GetZposfromZYXT = mData(3, 2)
End Function

' OK
Public Function GetXrotfromComb()
    GetXrotfromComb = mGamma
End Function
Public Function GetYrotfromComb()
    GetYrotfromComb = mBeta
End Function
Public Function GetZrotfromComb()
    GetZrotfromComb = mAlpha
End Function

Public Function Arcsin(x As Double) As Double
    If (Round(x, 5) = 1) Then
        Arcsin = PI / 2#
    ElseIf Round(x, 5) = -1 Then
        Arcsin = -PI / 2#
    Else
        Arcsin = Atn(x / Sqr(-x * x + 1#))
    End If
End Function

Public Sub ExecuteTXYZ()








    Dim c As New Collection
    c.Add mData(0, 2) / (1 - mData(0, 2) ^ 2), "tg(b)"
    
    c.Add mData(1, 0) + c.Item("tg(b)") * mData(1, 2) * mData(0, 0), "cos(g)*sin(a)"
    c.Add mData(2, 1) + c.Item("tg(b)") * mData(2, 2) * mData(0, 1), "sin(g)*cos(a)"
    c.Add mData(1, 1) + c.Item("tg(b)") * mData(1, 2) * mData(0, 1), "cos(g)*cos(a)"
    c.Add mData(2, 0) + c.Item("tg(b)") * mData(2, 2) * mData(0, 0), "sin(g)*sin(a)"
    
    c.Add c.Item("sin(g)*cos(a)") + c.Item("cos(g)*sin(a)"), "sin(a+g)"
    c.Add c.Item("cos(g)*sin(a)") - c.Item("sin(g)*cos(a)"), "sin(a-g)"
    c.Add c.Item("cos(g)*cos(a)") + c.Item("sin(g)*sin(a)"), "cos(a-g)"
    c.Add c.Item("cos(g)*cos(a)") - c.Item("sin(g)*sin(a)"), "cos(a+g)"
    
    c.Add c.Item("sin(g)*cos(a)") - c.Item("cos(g)*sin(a)"), "sin(g-a)"
    c.Add c.Item("cos(g)*cos(a)") + c.Item("sin(g)*sin(a)"), "cos(g-a)"
    
    c.Add myAsin(c.Item("sin(a+g)"), c.Item("cos(a+g)")), "a+g"
    c.Add myAsin(c.Item("sin(a-g)"), c.Item("cos(a-g)")), "a-g"
    
    c.Add myAsin(c.Item("sin(g-a)"), c.Item("cos(g-a)")), "g-a"
    
    c.Add c.Item("cos(g)*sin(a)") / c.Item("cos(g)*cos(a)"), "tg(a)"
    c.Add c.Item("sin(g)*cos(a)") / c.Item("cos(g)*cos(a)"), "tg(g)"
Metka:
    If c.Item("tg(a)") < c.Item("tg(g)") Then 'a>g - размышления, связанные с потерей 2*PI при сложении углов
        mAlpha = (c.Item("a+g") + c.Item("a-g")) / 2#
        mGamma = (c.Item("a+g") - c.Item("a-g")) / 2#
    Else
        mGamma = (c.Item("a+g") + c.Item("g-a")) / 2#
        mAlpha = (c.Item("a+g") - c.Item("g-a")) / 2#
    End If
    
    Dim cos_b As Double
    cos_b = mData(0, 0) / Cos(mAlpha)
    mBeta = myAsin(mData(0, 2), cos_b)
    
    
    
    
    
    
    
    
    
    
    
    
    
    
    
    
End Sub

Private Function myAsin(sin_a As Double, cos_a As Double)
    If (sin_a > 0) Then
        If (cos_a > 0) Then
            myAsin = Arcsin(sin_a)
        Else
            myAsin = PI - Arcsin(sin_a)
        End If
    Else
        If (cos_a > 0) Then
            myAsin = 2# * PI + Arcsin(sin_a)
        Else
            myAsin = PI - Arcsin(sin_a)
        End If
    End If
End Function

Public Sub Minor(o_minMat As Matrix, Ai As Integer, Aj As Integer)
    Dim v_minMas() As Double
    ReDim v_minMas(0 To mDimension - 1, 0 To mDimension - 1) As Double
    
    Dim i As Integer, j As Integer 'обход Me
    Dim Bi As Integer, Bj As Integer 'обход minMat
    Bi = 0
    Bj = 0
    
    For i = 0 To mDimension
        If i <> Ai Then
            For j = 0 To mDimension
                If j <> Aj Then
                    v_minMas(Bi, Bj) = mData(i, j)
                    Bj = Bj + 1
                End If
            Next j
            Bj = 0
            Bi = Bi + 1
        End If
    Next i
    
    o_minMat.SetDimension mDimension
    o_minMat.SetData v_minMas
End Sub

' Нахождение определителя матрицы
Public Function Det() As Double

    If (mDimension = 1) Then
        Det = mData(0, 0) * mData(1, 1) - mData(1, 0) * mData(0, 1)
        Exit Function
    End If
    
    Dim jCol As Integer
    Dim v_tempDet As Double
    Dim minMat As New Matrix
    
    Dim v_minus As Integer
    v_minus = 1
    
    For jCol = 0 To mDimension
        Me.Minor minMat, 0, jCol
        v_tempDet = v_tempDet + v_minus * mData(0, jCol) * minMat.Det()
        v_minus = v_minus * (-1)
    Next jCol
    Det = v_tempDet

End Function

' OK
' Деление матрицы на скаляр
Public Sub Divide(p_denominator As Double)
    Dim i As Integer, j As Integer
    For i = 1 To mDimension
        For j = 1 To mDimension
            mData(i, j) = mData(i, j) / p_denominator
        Next j
    Next i
End Sub

' OK
' Транспонирование матрицы
Public Sub Transpose()
    Dim i As Integer, j As Integer
    Dim v_temp As Double
    
    For i = 0 To mDimension
        For j = i + 1 To mDimension
            v_temp = mData(i, j)
            mData(i, j) = mData(j, i)
            mData(j, i) = v_temp
        Next j
    Next i
End Sub

Public Sub AdjugateMatrix(o_adMat As Matrix)
    Dim Ai As Integer, Aj As Integer
    Dim v_adMas() As Double
    ReDim v_adMas(0 To mDimension, 0 To mDimension) As Double
    
    Dim minMat As New Matrix
    
    For Ai = 0 To mDimension
        For Aj = 0 To mDimension
            Me.Minor minMat, Ai, Aj
            v_adMas(Ai, Aj) = ((-1) ^ (Ai + Aj)) * minMat.Det()
        Next Aj
    Next Ai
    
    o_adMat.SetDimension mDimension + 1
    o_adMat.SetData v_adMas
End Sub

' Нахождение обратной матрицы методом алгебраических дополнений
Public Sub Inverse()
    Dim v_revMat As New Matrix
    Me.AdjugateMatrix v_revMat
    v_revMat.Transpose
    v_revMat.Divide Me.Det()
    Me.Evaluate v_revMat
End Sub

' OK
Public Sub Evaluate(p_matrix As Matrix)
    Dim v_tmpArray() As Double
    ReDim v_tmpArray(0 To mDimension, 0 To mDimension) As Double
    p_matrix.GetData v_tmpArray
    Me.SetData v_tmpArray
End Sub

' OK
Public Sub EvaluateByAxisSys(p_axisSystem As myAxisSystem)
    Dim v_tmpVector(2) As Double

    p_axisSystem.GetXort v_tmpVector
    mData(0, 0) = v_tmpVector(0)
    mData(1, 0) = v_tmpVector(1)
    mData(2, 0) = v_tmpVector(2)

    p_axisSystem.GetYort v_tmpVector
    mData(0, 1) = v_tmpVector(0)
    mData(1, 1) = v_tmpVector(1)
    mData(2, 1) = v_tmpVector(2)

    p_axisSystem.GetZort v_tmpVector
    mData(0, 2) = v_tmpVector(0)
    mData(1, 2) = v_tmpVector(1)
    mData(2, 2) = v_tmpVector(2)

    p_axisSystem.GetCenter v_tmpVector
    mData(0, 3) = v_tmpVector(0)
    mData(1, 3) = v_tmpVector(1)
    mData(2, 3) = v_tmpVector(2)
    
    mData(3, 3) = 1#
End Sub

' OK
Public Sub EvaluateByBasis(p_Xort() As Double, p_Yort() As Double, p_Zort() As Double)
    mData(0, 0) = p_Xort(0)
    mData(0, 1) = p_Yort(0)
    mData(0, 2) = p_Zort(0)
    mData(0, 3) = 0#
    mData(1, 0) = p_Xort(1)
    mData(1, 1) = p_Yort(1)
    mData(1, 2) = p_Zort(1)
    mData(1, 3) = 0#
    mData(2, 0) = p_Xort(2)
    mData(2, 1) = p_Yort(2)
    mData(2, 2) = p_Zort(2)
    mData(2, 3) = 0#
    mData(3, 0) = 0#
    mData(3, 1) = 0#
    mData(3, 2) = 0#
    mData(3, 3) = 1#
End Sub

Public Sub EvaluateByTreeNode(p_node As ProdTreeNode)
    Me.EvaluateIdentity
    Me.MultiplyXYZposCol p_node.mX * 1000#, p_node.mY * 1000#, p_node.mZ * 1000#
    Me.MultiplyXrot p_node.mXRot
    Me.MultiplyYrot p_node.mYRot
    Me.MultiplyZrot p_node.mZRot
End Sub

Public Sub ApplyPosAndRotToFeature(translFeature As HybridShapeTranslate)

    Dim shps As Shapes
    Dim rotZfeature As HybridShapeRotate
    Dim rotYfeature As HybridShapeRotate
    Dim rotXfeature As HybridShapeRotate

    Set shps = translFeature.Parent
    Set rotZfeature = shps.Item("Rotate.Z")
    Set rotYfeature = shps.Item("Rotate.Y")
    Set rotXfeature = shps.Item("Rotate.X")

    translFeature.CoordXValue = Me.GetXposfromTXYZ / 1000#
    translFeature.CoordYValue = Me.GetYposfromTXYZ / 1000#
    translFeature.CoordZValue = Me.GetZposfromTXYZ / 1000#

    rotZfeature.AngleValue = Me.GetZrotfromComb * 180# / PI
    rotYfeature.AngleValue = Me.GetYrotfromComb * 180# / PI
    rotXfeature.AngleValue = Me.GetXrotfromComb * 180# / PI

End Sub

Public Function GetDimension() As Integer
    GetDimension = mDimension
End Function

Public Function GetElement(i As Integer, j As Integer) As Double
    GetElement = mData(i, j)
End Function

Public Sub SetElement(i As Integer, j As Integer, val As Double)
    mData(i, j) = val
End Sub

Attribute VB_Name = "MyCons"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myCons class

Option Explicit

Const TOLERANCE = 10

' -- Data members ----------------------------------------------------------------------

Dim pickedPoints(1 To 8) As HybridShapePointCoord

' pointer to singleton myFactory object
Dim myFac As myFactory

' temporary construct element
Dim checkPlanes(1 To 2) As HybridShapePlane3Points
Dim lines(1 To 5) As HybridShapeLinePtPt
Dim centers(1 To 2) As HybridShape 'Intersection
Dim Center As HybridShapePointBetween
Dim planes(1 To 4) As HybridShapePlane2Lines

Dim Zaxis As HybridShape
Dim Yaxis As HybridShapeIntersection
Dim Xaxis As HybridShapeLineAngle
Dim ZXplane As HybridShapePlane2Lines
Dim s As HybridShapeSphere
Dim Zorts As HybridShapeIntersection
Dim Xorts As HybridShapeIntersection
Dim Yorts As HybridShapeIntersection
Dim Zort As HybridShape
Dim Xort As HybridShape
Dim Yort As HybridShape
Dim Zort2 As HybridShape
Dim Xort2 As HybridShape
Dim Yort2 As HybridShape

' recognized parameters
Dim pRmin1 As Double
Dim pRmax1 As Double
Dim pRmin2 As Double
Dim pRmax2 As Double
Dim pDz As Double
Dim pSPhi As Double
Dim pDPhi As Double

' recognized axis system
Dim mAxisSystem As New myAxisSystem

' -- Methods ---------------------------------------------------------------------------

Public Sub SetFactory(ByRef p_fac As myFactory)

    Set myFac = p_fac

End Sub

Public Sub SetPickedPoints(p1 As HybridShapePointCoord, p2 As HybridShapePointCoord, _
                            p3 As HybridShapePointCoord, p4 As HybridShapePointCoord, _
                            p5 As HybridShapePointCoord, p6 As HybridShapePointCoord, _
                            p7 As HybridShapePointCoord, p8 As HybridShapePointCoord)

    Set pickedPoints(1) = p1
    Set pickedPoints(2) = p2
    Set pickedPoints(3) = p3
    Set pickedPoints(4) = p4
    Set pickedPoints(5) = p5
    Set pickedPoints(6) = p6
    Set pickedPoints(7) = p7
    Set pickedPoints(8) = p8

End Sub

Public Sub SetPickedPoints2(pts() As HybridShapePointCoord)

    Me.SetPickedPoints pts(1), pts(2), pts(3), pts(4), pts(5), pts(6), pts(7), pts(8)

End Sub

Public Sub BuildConstructPre()
    'Первая линия - по нижнему радиусу
    myFac.BuildLine pickedPoints(1), pickedPoints(4), lines(1), "line.AB"
    'Вторая - по верхнему радиусу
    myFac.BuildLine pickedPoints(2), pickedPoints(3), lines(2), "line.CD"
    'Третья, четвертая по нижнему/верхнему аналогично
    myFac.BuildLine pickedPoints(5), pickedPoints(8), lines(3), "line.EF"
    myFac.BuildLine pickedPoints(6), pickedPoints(7), lines(4), "line.GH"

    ' Update
    myFac.myUpdate

End Sub

Public Sub FixPointsOrder()

    'Обязываем пользователя делать обкликивания точек начиная с нижнего внешнего радиуса по направляющей

End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8

    ' Update
    myFac.myUpdate

    ' Check planarity of the selected groups of points
    formPrimitiveCreator.TextBox2.Text = myFac.GetDistance(checkPlanes(1), pickedPoints(4))
    formPrimitiveCreator.TextBox3.Text = myFac.GetDistance(checkPlanes(2), pickedPoints(8))

    ' Build the center of the primitive in two different ways
    Dim flag As Integer
    flag = 0
    'check if pDPhi=180
    If myFac.GetAngle(lines(2), lines(4)) = 180 Or myFac.GetAngle(lines(2), lines(4)) = 0 Then
      myFac.BuildMidPoint2 pickedPoints(4), pickedPoints(8), centers(1), "center.1" 'bottom
      myFac.BuildMidPoint2 pickedPoints(3), pickedPoints(7), centers(2), "center.2" 'top
      flag = 1
    Else
      myFac.BuildIntersectionPoint lines(1), lines(3), centers(1), "center.1" 'bottom
      myFac.BuildIntersectionPoint lines(2), lines(4), centers(2), "center.2" 'top
    End If
     myFac.BuildMidPoint2 centers(1), centers(2), Center, "center"
     ' Check that the center of the primitive found two different ways is the same within tolerance
     
    myFac.myUpdate
    formPrimitiveCreator.TextBox1.Text = myFac.GetDistance(centers(1), centers(2))
    ' Build bounding planes
    myFac.BuildPlane lines(1), lines(2), planes(3), "plane.1.phi"
    myFac.BuildPlane lines(3), lines(4), planes(4), "plane.2.phi"
    myFac.myUpdate
    
    ' Build axes of the primitive
    myFac.BuildParallelLine lines(1), planes(3), Center, Xaxis, "XaxisOfThePrimitive"
    If flag = 0 Then
        myFac.BuildIntersectionLine planes(3), planes(4), Zaxis, "ZaxisOfThePrimitive"
    Else
        myFac.BuildLine centers(1), centers(2), Zaxis, "ZaxisOfThePrimitive"
        Zaxis.SetLengthType 1
    End If
     myFac.myUpdate
    ' Build YZ plane of the primitive
    myFac.BuildPlane Zaxis, Xaxis, ZXplane, "plane.ZX"
   ' myFac.BuildNormalToPlane YZplane, centers(1), Xaxis, "XaxisOfThePrimitive"

    ' Update
    myFac.myUpdate

    ' Build a sphere, its intersection with the Z axis and 'near' to define the positive direction of the Z axis
    myFac.BuildSphere Center, 1#, s, "sphere.identity"
    myFac.BuildIntersection s, Zaxis, Zorts, "Zorts"
    myFac.BuildIntersection s, Xaxis, Xorts, "Xorts"
   ' myFac.BuildIntersection s, Yaxis, Yorts, "Yorts"
   'определяем положительное направление орта Z как точку(из двух) ближайшую к верхнему основанию
    myFac.SelectNearestPoint Zorts, centers(2), Zort, "Zort"
    'определяем положительное направление орта X как точку(из двух) ближайшую к первой прямой
    '
    myFac.SelectNearestPoint Xorts, lines(1), Xort, "Xort"
   ' myFac.SelectNearestPoint Yorts, lines(1), Yort, "Yort"
    myFac.BuildPoint Zort, Zort2, "Zort2"
    myFac.BuildPoint Xort, Xort2, "Xort2"
   ' myFac.BuildPoint Yort, Yort2, "Yort2"

    ' Update
    myFac.myUpdate
    
    
    ' Compute coordinate system
    Dim v_pointToExtractCoordinates
    Dim v_tmpVariant(2)
    Dim v_tmpDouble(2) As Double
    Dim v_tmpCenter(2) As Double
    Dim centaxis As HybridShape
    Dim cent
    
    myFac.Center Center, v_tmpCenter
    mAxisSystem.SetCenter v_tmpCenter    ' Set center of the axis system

    Set v_pointToExtractCoordinates = Xort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetXort v_tmpDouble      ' Set Z direction of the axis system

  '  Set v_pointToExtractCoordinates = Yort2
  '  v_pointToExtractCoordinates.GetCoordinates v_tmpVariant
  '  v_tmpDouble(0) = v_tmpVariant(0) - v_tmpCenter(0)
  '  v_tmpDouble(1) = v_tmpVariant(1) - v_tmpCenter(1)
  '  v_tmpDouble(2) = v_tmpVariant(2) - v_tmpCenter(2)
  '  mAxisSystem.SetYort v_tmpDouble      ' Set X direction of the axis system
    
    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Y direction of the axis system
    

    mAxisSystem.ComputeYort              ' Compute the last Y direction from given Z and X directions
  '   mAxisSystem.ComputeXort
  '  mAxisSystem.ComputeZort

End Sub

Public Sub Recognize()

    ' Compute pRmin1
    Dim Rmin1 As Double
    Rmin1 = myFac.GetDistance(centers(1), pickedPoints(4))
    pRmin1 = Round(Rmin1, TOLERANCE)
    formPrimitiveCreator.ListBox1.AddItem "pRmin1 = " & pRmin1

    ' Compute pRmax1
    Dim Rmax1 As Double
    Rmax1 = myFac.GetDistance(centers(1), pickedPoints(1))
    pRmax1 = Round(Rmax1, TOLERANCE)
    formPrimitiveCreator.ListBox1.AddItem "pRmax1 = " & pRmax1
    
    ' Compute pRmin2
    Dim Rmin2 As Double
    Rmin2 = myFac.GetDistance(centers(2), pickedPoints(3))
    pRmin2 = Round(Rmin2, TOLERANCE)
    formPrimitiveCreator.ListBox1.AddItem "pRmin2 = " & pRmin2

    ' Compute pRmax2
    Dim Rmax2 As Double
    Rmax2 = myFac.GetDistance(centers(2), pickedPoints(2))
    pRmax2 = Round(Rmax2, TOLERANCE)
    formPrimitiveCreator.ListBox1.AddItem "pRmax2 = " & pRmax2
    
    ' Compute pDz
    Dim Dz As Double
    Dz = myFac.GetDistance(centers(1), centers(2)) / 2#
    pDz = Round(Dz, TOLERANCE)
    formPrimitiveCreator.ListBox1.AddItem "pDz = " & pDz
    
    ' Compute pDPhi
    DPhi = myFac.GetAngle(planes(3), planes(4))
    pDPhi = Round(DPhi, TOLERANCE)
    Call checkDPhi
    myFac.myUpdate
    formPrimitiveCreator.ListBox1.AddItem "pDPhi = " & pDPhi
    
    ' Compute pSPhi
    'Dim SPhi As Double
    'SPhi = DPhi / 2#
    'pSPhi = Round(SPhi, TOLERANCE)
    pSPhi = pDPhi / 2
    formPrimitiveCreator.ListBox1.AddItem "pSPhi = " & pSPhi
    
    End Sub
Public Sub GetAxisSystem(ByRef o_axSystem As myAxisSystem)
    Set o_axSystem = mAxisSystem
End Sub
Public Sub ApplyParametersToUDF(shpInst As ShapeInstance)

    Call shpInst.GetParameter("pRmin1").ValuateFromString(Trim(Str(pRmin1)) + "mm")
    Call shpInst.GetParameter("pRmax1").ValuateFromString(Trim(Str(pRmax1)) + "mm")
    Call shpInst.GetParameter("pRmin2").ValuateFromString(Trim(Str(pRmin2)) + "mm")
    Call shpInst.GetParameter("pRmax2").ValuateFromString(Trim(Str(pRmax2)) + "mm")
    Call shpInst.GetParameter("pDz").ValuateFromString(Trim(Str(pDz)) + "mm")
    Call shpInst.GetParameter("pDPhi").ValuateFromString(Trim(Str(pDPhi)) + "deg")
    Call shpInst.GetParameter("pSPhi").ValuateFromString(Trim(Str(pSPhi)) + "deg")


End Sub

Public Sub checkDPhi()
    Dim mtrxData(2, 2) As Double
    Dim tmpData(2) As Double

    Dim pointToGetCoords
    Dim coords1(2) As Variant
    Dim coords2(2) As Variant

    Call mAxisSystem.GetZort(tmpData)
    mtrxData(0, 0) = tmpData(0)
    mtrxData(0, 1) = tmpData(1)
    mtrxData(0, 2) = tmpData(2)

    Call mAxisSystem.GetXort(tmpData)
    mtrxData(1, 0) = tmpData(0)
    mtrxData(1, 1) = tmpData(1)
    mtrxData(1, 2) = tmpData(2)
    
    Set pointToGetCoords = pickedPoints(6) 'внешняя верхняя точка
    pointToGetCoords.GetCoordinates coords1
    Set pointToGetCoords = pickedPoints(7) 'внутренняя верхняя точка
    pointToGetCoords.GetCoordinates coords2

    Call mAxisSystem.GetXort(tmpData)
    mtrxData(2, 0) = coords1(0) - coords2(0)
    mtrxData(2, 1) = coords1(1) - coords2(1)
    mtrxData(2, 2) = coords1(2) - coords2(2)

    Dim MatrixZX As New Matrix
    MatrixZX.SetDimension 3
    MatrixZX.SetData mtrxData
               
    Call mAxisSystem.GetYort(tmpData)
    mtrxData(1, 0) = tmpData(0)
    mtrxData(1, 1) = tmpData(1)
    mtrxData(1, 2) = tmpData(2)

    Dim MatrixZY As New Matrix
    MatrixZY.SetDimension 3
    MatrixZY.SetData mtrxData
            
    '>270 + -
    '>180 + +
    '>90 - +
    '>0 - -
    
    
    ' Det of       Det of       Quarter of
' MatrixZX     MatrixZY     Phi angle
'    -            -             I
'    -            +             II
'    +            +             III
'    +            -             IV
    If (pDPhi > 0# And pDPhi <= 90#) Then
        If (MatrixZX.Det > 0#) Then
            If (MatrixZY.Det > 0#) Then
                ' III
                pDPhi = pDPhi + 180#
            Else
                ' IV
                pDPhi = 360# - pDPhi
            End If
        Else
            If (MatrixZY.Det < 0#) Then
                ' I
                'ok
                pDPhi = pDPhi
            Else
                ' II
                pDPhi = 180# - pDPhi
            End If
        End If
    ElseIf (pDPhi > 90# And pDPhi <= 180#) Then
        If (MatrixZX.Det > 0#) Then
            If (MatrixZY.Det > 0#) Then
                ' III
                pDPhi = 360# - pDPhi
            Else
                ' IV
                pDPhi = 180# + pDPhi
            End If
        Else
            If (MatrixZY.Det < 0#) Then
                ' I
                pDPhi = 180# - pDPhi
            Else
                ' II
                pDPhi = pDPhi
            End If
        End If
    ElseIf (pDPhi = 0# Or pDPhi = 180#) Then
            pDPhi = 180#
    Else
        MsgBox "Warning. Strange DPhi computed.", vbExclamation
    End If
   
End Sub

Attribute VB_Name = "ProdBranch"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' ProdBranch class

Option Explicit

Public Sub Init(tr As HybridShapeTranslate)
    Dim shps As Shapes
    Set shps = tr.Parent
    Dim prt As Part ' The part being positioned
    Dim bd As Body
    Dim motherPrt As Part 'if nothing -> boolean operand->current part coordinate sys
    Set bd = shps.Parent
    If Left(shps.Item(1).Name, 2) = "G4" Then   'boolean operand
        Set prt = bd.Parent.Parent
        Set motherPrt = Nothing
    Else                                        'volume
        Dim srcProd As Product
        Set srcProd = shps.Item(1).SourceProduct
        Dim prtDoc As PartDocument
        Set prtDoc = srcProd.ReferenceProduct.Parent
        Set prt = prtDoc.Part
        Set motherPrt = bd.Parent.Parent
    End If
    Dim prTree As New ProdTree
    prTree.CreateTree prt, motherPrt
End Sub

Attribute VB_Name = "ProdTree"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' ProdTree class

Option Explicit

Dim mStartNode As ProdTreeNode
Dim mFinishPrt As Part
Dim mMotherPrt As Part

' Конструктор по умолчанию
Private Sub Class_Initialize()
    Set mStartNode = Nothing
End Sub

' Дерево продукта строится до finishPrt
Public Sub CreateTree(ByRef finishPrt As Part, motherPrt As Part)
    Set mFinishPrt = finishPrt
    
    Dim prodDoc As ProductDocument
    Set prodDoc = CATIA.ActiveDocument
    Dim subProds As Products
    Set subProds = prodDoc.Product.Products
    Dim topProd As Product
    Set topProd = subProds.Item(subProds.Count)
    Dim topPrt As Part
    Set topPrt = CATIA.Documents.Item(topProd.PartNumber & ".CATPart").Part
    
    'Классический обход дерева в ширину: берем первый элемент из очереди, строим его дочерние узлы и добовляем их в конец очереди
    Dim queue As New Collection 'очередь для обхода G4 дерева в ширину
    
    'Инициализация стартового узла
    Set mStartNode = New ProdTreeNode
    Set mStartNode.mPrt = topPrt
    
    queue.Add mStartNode
    
    Dim newNode As ProdTreeNode, curNode As ProdTreeNode
    Dim newNodeShp As Shape
    Dim rot As Rotate
    Dim trans As Translate
    Dim i_body As Integer, i_shape As Integer
    
    Do While (queue.Count > 0)
        Set curNode = queue.Item(1)
        For i_body = 2 To curNode.mPrt.bodies.Count
            Set newNode = New ProdTreeNode
            Set newNode.mMotherNode = curNode
            curNode.mOutputNodes.Add newNode
            Set newNodeShp = curNode.mPrt.bodies.Item(i_body).Shapes.Item(1)
            Set newNode.mPrt = CATIA.Documents.Item(newNodeShp.SourceProduct.PartNumber & ".CATPart").Part
            For i_shape = 2 To newNodeShp.Parent.Count
                If Left(newNodeShp.Parent.Item(i_shape).Name, 8) = "Rotate.X" Then
                    Set rot = newNodeShp.Parent.Item(i_shape)
                    newNode.mXRot = rot.AngleValue
                ElseIf Left(newNodeShp.Parent.Item(i_shape).Name, 8) = "Rotate.Y" Then
                    Set rot = newNodeShp.Parent.Item(i_shape)
                    newNode.mYRot = rot.AngleValue
                ElseIf Left(newNodeShp.Parent.Item(i_shape).Name, 8) = "Rotate.Z" Then
                    Set rot = newNodeShp.Parent.Item(i_shape)
                    newNode.mZRot = rot.AngleValue
                ElseIf Left(newNodeShp.Parent.Item(i_shape).Name, 9) = "Translate" Then
                    Set trans = newNodeShp.Parent.Item(i_shape)
                    newNode.mX = trans.HybridShape.CoordXValue
                    newNode.mY = trans.HybridShape.CoordYValue
                    newNode.mZ = trans.HybridShape.CoordZValue
                End If
            Next i_shape
            queue.Add newNode

            If (newNode.mPrt.Name = mFinishPrt.Name) Then
                If motherPrt Is Nothing Then
                    Exit Do
                Else
                    If curNode.mPrt.Name = motherPrt.Name Then
                        Exit Do
                    End If
                End If
            End If
        Next i_body
        queue.Remove (1)
    Loop
End Sub

' Возвращает матрицу перехода от абсолютной СК к СК заданного парта
Public Sub createTransportMatrixToPart(tranMat As Matrix, prt As Part, motherPrt As Part)
    
    Dim prtNode As ProdTreeNode
    Set prtNode = findNode(prt, motherPrt, mStartNode)
    Dim curNode As ProdTreeNode
    If Not (motherPrt Is Nothing) Then
        Set curNode = prtNode.mMotherNode
    Else
        Set curNode = prtNode
    End If
    Dim tempMat As New Matrix
    tempMat.SetDimension 4
    
    tranMat.EvaluateIdentity
    
    Do While Not (curNode.mMotherNode Is Nothing)
        tempMat.EvaluateByTreeNode curNode
        tempMat.Multiply tranMat
        tranMat.Evaluate tempMat

        Set curNode = curNode.mMotherNode
    Loop
End Sub

' Поиск узла вглубину начиная с узла findLevel
Private Function findNode(prt As Part, motherPrt As Part, findLevel As ProdTreeNode) As ProdTreeNode
    If Not (findLevel.mMotherNode Is Nothing) Then
        If (prt.Name = findLevel.mPrt.Name) Then
            If motherPrt Is Nothing Then
                Set findNode = findLevel
                Exit Function
            Else
                 If findLevel.mMotherNode.mPrt.Name = motherPrt.Name Then
                     Set findNode = findLevel
                     Exit Function
                 End If
            End If
        End If
    End If
    Dim i As Integer
    For i = 1 To findLevel.mOutputNodes.Count
        Set findNode = findNode(prt, motherPrt, findLevel.mOutputNodes.Item(i))
    Next i

End Function

Public Sub Init(tr As HybridShapeTranslate)
    Dim shps As Shapes
    Set shps = tr.Parent
    Dim prt As Part ' The part being positioned
    Dim bd As Body
    Dim motherPrt As Part 'if nothing -> boolean operand->current part coordinate sys
    Set bd = shps.Parent
    If Left(shps.Item(1).Name, 2) = "G4" Then   'boolean operand
        Set prt = bd.Parent.Parent
        Set motherPrt = Nothing
    Else                                        'volume
        Dim srcProd As Product
        Set srcProd = shps.Item(1).SourceProduct
        Dim prtDoc As PartDocument
        Set prtDoc = srcProd.ReferenceProduct.Parent
        Set prt = prtDoc.Part
        Set motherPrt = bd.Parent.Parent
    End If
    Set mMotherPrt = motherPrt
    Me.CreateTree prt, motherPrt
End Sub

Public Sub createTransportMatrixToFinishPart(trMat As Matrix)
    Me.createTransportMatrixToPart trMat, mFinishPrt, mMotherPrt
End Sub

Attribute VB_Name = "ProdTreeNode"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' ProdTreeNode class

Option Explicit

Public mPrt  As Part 'ссылка на Part которому соответствует узел
Public mZRot As Double
Public mYRot As Double
Public mXRot As Double
Public mX As Double
Public mY As Double
Public mZ As Double
Public mOutputNodes As New Collection
Public mMotherNode As ProdTreeNode

Attribute VB_Name = "Scanner"
Sub CATMain()

    formTrapScanner.Show vbModeless

End Sub

Attribute VB_Name = "StartPrimitiveCreator"
Sub CATMain()

    formPrimitiveCreator.Show vbModeless

End Sub

Attribute VB_Name = "formPrimitiveCreator"
Attribute VB_Base = "0{64966114-95FF-4A33-ABB7-4553D7C1083B}{64D9988E-B286-4EFE-A253-4D21F07FC0CA}"
Attribute VB_GlobalNameSpace = False
Attribute VB_Creatable = False
Attribute VB_PredeclaredId = True
Attribute VB_Exposed = False
Attribute VB_TemplateDerived = False
Attribute VB_Customizable = False
Option Explicit

Private Sub cmbStart_Click()
    'get tool class object
    Dim myFac As New myFactory
    Call myFac.Init

    'read 8 point selected by the user
    Dim pts(1 To 8) As HybridShapePointCoord
    Call myFac.SelectAndBuildPoint(pts(1), lstFirstPlane, "point.A", True)
    Call myFac.SelectAndBuildPoint(pts(2), lstFirstPlane, "point.B", False)
    Call myFac.SelectAndBuildPoint(pts(3), lstFirstPlane, "point.C", False)
    Call myFac.SelectAndBuildPoint(pts(4), lstFirstPlane, "point.D", False)

    Call myFac.SelectAndBuildPoint(pts(5), lstSecondPlane, "point.E", False)
    Call myFac.SelectAndBuildPoint(pts(6), lstSecondPlane, "point.F", False)
    Call myFac.SelectAndBuildPoint(pts(7), lstSecondPlane, "point.G", False)
    Call myFac.SelectAndBuildPoint(pts(8), lstSecondPlane, "point.H", False)
    Call myFac.myUpdate

    'get the type of the primitive from the form
    Dim prim
    Select Case ListOfPrimitives.Text
    Case "Trap": Set prim = New myTrap
    Case "Trd": Set prim = New myTrd
    Case "Cons": Set prim = New MyCons
    Case "Sphere": Set prim = New mySphere
    Case "Para": Set prim = New myPara
    Case "Box": Set prim = New myBox
    Case "Tubs": Set prim = New myTubs
    End Select

    'set the factory for the primitive
    Call prim.SetFactory(myFac)
    'set the points for recognition
    Call prim.SetPickedPoints2(pts)
    'generate the first set of construction elements
    Call prim.BuildConstructPre
    'check the first set of construction elements, fix them if needed
    Call prim.FixPointsOrder
    'generate the second set of construction elements
    Call prim.BuildConstructPost
    'recognize the primitive - define its parameters and position
    Call prim.Recognize

    ' myFac.Cleanup

    ' ---------------- Apply shape ----------------

    Dim sphInst As ShapeInstance
    Call myFac.SelectShape(sphInst)

    Call prim.ApplyParametersToUDF(sphInst)
    Call myFac.myUpdate 'TODO check that it is needed here

    ' ---------------- Apply positioning ----------------

    'vol1   -M1                                                          (M*) = |p(1)   q(1)    norm(1)     Xloc|
    '  |       |                                                                |p(2)   q(2)    norm(2)     Yloc|
    '  |        ->vol2   -M2                                                    |p(3)   q(3)    norm(3)     Zloc|
    '  |                  |                                                     |0      0       0           1   |
    '  |                  -> vol3 -M3
    '  |                            |
    '  (M*) ------->                   -> trap                              Xloc,Yloc,Zloc - center of local basis
    '
    ' M1 = T*Xrot*Yrot*Ztor (M2...)                                        T = |0 0 0 Xtr|
    '                                                                          |0 0 0 Ytr|
    '                                                                          |0 0 0 Ztr|
    '
    '(M*) = M1*M2*M3
    '   M3 = ((M1*M2)^-1)*(M*)
    
    Dim translFeature As HybridShapeTranslate
    Call myFac.SelectTranslate(translFeature)

    ' Transformation matrix from global to local basis  (M1*M2*...)^1
    Dim trMatrix As New Matrix
    Call trMatrix.SetDimension(4)

    Dim prTree As New ProdTree
    Call prTree.Init(translFeature)
    'Create M1*M2*... from tree
    Call prTree.createTransportMatrixToFinishPart(trMatrix)
    'Inverse M1*M2*... -> (M1*M2*...)^-1
    Call trMatrix.Inverse

    ' (M*) creation
    Dim primitiveMat As New Matrix
    Call primitiveMat.SetDimension(4)
    Dim primAxisSys As New myAxisSystem
    Call prim.GetAxisSystem(primAxisSys)
    Call primitiveMat.EvaluateByAxisSys(primAxisSys)

    'M3 = ((M1*M2)^-1)*(M*)
    Call trMatrix.Multiply(primitiveMat)

    Call trMatrix.ExecuteTXYZ
    Call trMatrix.ApplyPosAndRotToFeature(translFeature)

    Call myFac.myUpdate

End Sub

Private Sub cmbExit_Click()
    End
End Sub

Private Sub UserForm_Initialize()

    ListOfPrimitives.AddItem "Trap"
    ListOfPrimitives.AddItem "Trd"
    ListOfPrimitives.AddItem "Sphere"
    ListOfPrimitives.AddItem "Cons"
    ListOfPrimitives.AddItem "Tubs"
    ListOfPrimitives.AddItem "Para"
    ListOfPrimitives.AddItem "Box"
    
End Sub

Attribute VB_Name = "formTrapScanner"
Attribute VB_Base = "0{0E79B0EA-2A48-444D-8203-63954AC9131B}{7866EB02-5CFF-4781-A268-981C608588C7}"
Attribute VB_GlobalNameSpace = False
Attribute VB_Creatable = False
Attribute VB_PredeclaredId = True
Attribute VB_Exposed = False
Attribute VB_TemplateDerived = False
Attribute VB_Customizable = False
Option Explicit

Dim prodDoc As ProductDocument
Dim sel As Selection
Dim docs As Documents
Dim prtDoc As PartDocument
Dim prt As Part
Dim prtBody As Body
Dim mBody As Body
Dim bodies As bodies
Dim HybridShps As HybridShapes
Dim HybridShapeRotateX As HybridShapeRotate
Dim HybridShapeRotateY As HybridShapeRotate
Dim HybridShapeRotateZ As HybridShapeRotate
Dim RotX As Rotate
Dim RotY As Rotate
Dim RotZ As Rotate
Dim pts(1 To 8) As HybridShapePointCoord
Dim myFac As New myFactory
Dim mFactory As HybridShapeFactory
Dim prim As New myTrap
Dim sphInst As ShapeInstance
Dim translFeature As HybridShapeTranslate
Dim trMatrix As New Matrix
Dim prTree As New ProdTree
Dim primitiveMat As New Matrix
Dim primAxisSys As New myAxisSystem
Dim shpFactory As ShapeFactory
Dim mRemove As Remove
Dim params As Parameters

Dim AngleAlpha As Angle
Dim AngleTheta As Angle
Dim AnglePhi As Angle

Dim i_alpha As Integer
Dim i_theta As Integer
Dim i_phi As Integer

Private Sub cbmAlphaScan_Click()

    Dim numOfIters As Integer
    numOfIters = 12 * 18 * 19
    
    Dim i As Integer

    For i = 1 To numOfIters
        Call cmbAlpha_Click
    Next i

End Sub

Private Sub cmbAlpha_Click()
    Call DoIter(1)
End Sub
Private Sub cmbTheta_Click()
    Call DoIter(2)
End Sub
Private Sub cmbPhi_Click()
    Call DoIter(3)
End Sub

Private Sub CommandButton2_Click()
    End
End Sub

Private Sub CommandButton3_Click()
    Dim sFile As String, lFile As Long
    sFile = "E:\Documents\Scan1.txt"
    lFile = FreeFile
    Open sFile For Append As lFile
    Dim i As Integer
    For i = 0 To ListBox1.ListCount - 1
        Print #lFile, ListBox1.list(i)
    Next i
    Close lFile
End Sub

Private Sub ToggleButton1_Change()
    If ToggleButton1.Value = True Then
        formTrapScanner.Width = 450
    Else
        formTrapScanner.Width = 102
    End If
End Sub

' alpha - i_alpha = (-90; 90)  => [-88; 88] step 16 - total 12
' theta - i_theta = [0; 90) => [0; 85] step 5       - total 18
' phi -   i_phi   = [-180; 180] step 10 (20)        - total (19)

Private Sub UserForm_Initialize()
    
    Set prodDoc = CATIA.ActiveDocument
    Set sel = prodDoc.Selection
    Set docs = CATIA.Documents
    Set prtDoc = docs.Item("Generic_trap_CAD.CATPart")
    Set prt = prtDoc.Part
    Set bodies = prt.bodies
    Set prtBody = bodies.Item("PartBody")
    Set HybridShps = prtBody.HybridShapes
    Set HybridShapeRotateX = HybridShps.Item("Rotate.X")
    Set HybridShapeRotateY = HybridShps.Item("Rotate.Y")
    Set HybridShapeRotateZ = HybridShps.Item("Rotate.Z")
    Set params = prt.Parameters
    Set AngleAlpha = params.Item("Generic_trap_CAD\PartBody\G4Trap.1\pAlp1")
    Set AngleTheta = params.Item("Generic_trap_CAD\PartBody\G4Trap.1\pTheta")
    Set AnglePhi = params.Item("Generic_trap_CAD\PartBody\G4Trap.1\pPhi")

    i_alpha = -88
    i_theta = 0
    i_phi = -60

    formTrapScanner.txtAlpha.Text = Str(i_alpha)
    formTrapScanner.txtTheta.Text = Str(i_theta)
    formTrapScanner.txtPhi.Text = Str(i_phi)

End Sub

' mode: 1 - alpha, 2 - theta, 3 - phi
Public Sub NextIter(mode As Integer)

    Dim step_alpha As Integer
    Dim step_theta As Integer
    Dim step_phi As Integer

    step_alpha = 16
    step_theta = 5
    step_phi = -20 ' 10

    Select Case mode
    
    Case 1 ' alpha
        i_alpha = i_alpha + step_alpha
        If (i_alpha >= 88 + step_alpha) Then
            i_alpha = -88

            i_theta = i_theta + step_theta
            If (i_theta >= 85 + step_theta) Then
                i_theta = 0

                i_phi = i_phi + step_phi
                If (i_phi <= -180 + step_phi) Then
                    i_phi = 0


                End If

            End If

        End If
  
    Case 2 ' theta
        i_theta = i_theta + step_theta
        If (i_theta >= 85 + step_theta) Then
            i_theta = 0
            
            i_phi = i_phi + step_phi
            If (i_phi <= -180 + step_phi) Then
                i_phi = 0

                i_alpha = i_alpha + step_alpha
                If (i_alpha >= 88 + step_alpha) Then
                    i_alpha = -88


                End If
    
            End If

        End If
    
    Case 3 ' phi
        i_phi = i_phi + step_phi
        If (i_phi <= -180 + step_phi) Then
            i_phi = 0

            i_theta = i_theta + step_theta
            If (i_theta >= 85 + step_theta) Then
                i_theta = 0

                i_alpha = i_alpha + step_alpha
                If (i_alpha >= 88 + step_alpha) Then
                    i_alpha = -88


                End If

            End If

        End If
    
    End Select

    formTrapScanner.txtAlpha.Text = Str(i_alpha)
    formTrapScanner.txtTheta.Text = Str(i_theta)
    formTrapScanner.txtPhi.Text = Str(i_phi)

End Sub

' mode: 1 - alpha, 2 - theta, 3 - phi
Public Sub DoIter(mode As Integer)

        AngleAlpha.Value = i_alpha
        AngleTheta.Value = i_theta
        AnglePhi.Value = i_phi
        prt.Update

        Dim anglesString As String
        anglesString = "Alpha=" & i_alpha & "   Theta=" & i_theta & "   Phi=" & i_phi
    
        Call myFac.Init2
        Call myFac.SelectAndBuildPoint2(pts(1), "FVertex:(Vertex:(Neighbours:(Face:(Brp:(G4Trap.1;(Brp:(G4Trap.1_GSMLoft.1;(Brp:(Sketch.2;1);Brp:(Sketch.2;2);Brp:(Sketch.2;3);Brp:(Sketch.2;4)))));None:();Cf11:());Face:(Brp:(G4Trap.1;(Brp:(G4Trap.1_GSMLoft.1;(Brp:(Sketch.1;3);Brp:(Sketch.2;3)))));None:();Cf11:());Face:(Brp:(G4Trap.1;(Brp:(G4Trap.1_GSMLoft.1;(Brp:(Sketch.1;4);Brp:(Sketch.2;4)))));None:();Cf11:()));Cf11:());WithPermanentBody;WithoutBuildError;WithSelectingFeatureSupport;MFBRepVersion_CXR15)", "point.A", HybridShapeRotateX, True)
        Call myFac.SelectAndBuildPoint2(pts(2), "FVertex:(Vertex:(Neighbours:(Face:(Brp:(G4Trap.1;(Brp:(G4Trap.1_GSMLoft.1;(Brp:(Sketch.2;1);Brp:(Sketch.2;2);Brp:(Sketch.2;3);Brp:(Sketch.2;4)))));None:();Cf11:());Face:(Brp:(G4Trap.1;(Brp:(G4Trap.1_GSMLoft.1;(Brp:(Sketch.1;3);Brp:(Sketch.2;3)))));None:();Cf11:());Face:(Brp:(G4Trap.1;(Brp:(G4Trap.1_GSMLoft.1;(Brp:(Sketch.1;2);Brp:(Sketch.2;2)))));None:();Cf11:()));Cf11:());WithPermanentBody;WithoutBuildError;WithSelectingFeatureSupport;MFBRepVersion_CXR15)", "point.B", HybridShapeRotateX, False)
        Call myFac.SelectAndBuildPoint2(pts(3), "FVertex:(Vertex:(Neighbours:(Face:(Brp:(G4Trap.1;(Brp:(G4Trap.1_GSMLoft.1;(Brp:(Sketch.2;1);Brp:(Sketch.2;2);Brp:(Sketch.2;3);Brp:(Sketch.2;4)))));None:();Cf11:());Face:(Brp:(G4Trap.1;(Brp:(G4Trap.1_GSMLoft.1;(Brp:(Sketch.1;2);Brp:(Sketch.2;2)))));None:();Cf11:());Face:(Brp:(G4Trap.1;(Brp:(G4Trap.1_GSMLoft.1;(Brp:(Sketch.1;1);Brp:(Sketch.2;1)))));None:();Cf11:()));Cf11:());WithPermanentBody;WithoutBuildError;WithSelectingFeatureSupport;MFBRepVersion_CXR15)", "point.C", HybridShapeRotateX, False)
        Call myFac.SelectAndBuildPoint2(pts(4), "FVertex:(Vertex:(Neighbours:(Face:(Brp:(G4Trap.1;(Brp:(G4Trap.1_GSMLoft.1;(Brp:(Sketch.1;1);Brp:(Sketch.2;1)))));None:();Cf11:());Face:(Brp:(G4Trap.1;(Brp:(G4Trap.1_GSMLoft.1;(Brp:(Sketch.2;1);Brp:(Sketch.2;2);Brp:(Sketch.2;3);Brp:(Sketch.2;4)))));None:();Cf11:());Face:(Brp:(G4Trap.1;(Brp:(G4Trap.1_GSMLoft.1;(Brp:(Sketch.1;4);Brp:(Sketch.2;4)))));None:();Cf11:()));Cf11:());WithPermanentBody;WithoutBuildError;WithSelectingFeatureSupport;MFBRepVersion_CXR15)", "point.D", HybridShapeRotateX, False)
        Call myFac.SelectAndBuildPoint2(pts(5), "FVertex:(Vertex:(Neighbours:(Face:(Brp:(G4Trap.1;(Brp:(G4Trap.1_GSMLoft.1;(Brp:(Sketch.1;3);Brp:(Sketch.2;3)))));None:();Cf11:());Face:(Brp:(G4Trap.1;(Brp:(G4Trap.1_GSMLoft.1;(Brp:(Sketch.1;4);Brp:(Sketch.2;4)))));None:();Cf11:());Face:(Brp:(G4Trap.1;(Brp:(G4Trap.1_GSMLoft.1;(Brp:(Sketch.1;1);Brp:(Sketch.1;2);Brp:(Sketch.1;3);Brp:(Sketch.1;4)))));None:();Cf11:()));Cf11:());WithPermanentBody;WithoutBuildError;WithSelectingFeatureSupport;MFBRepVersion_CXR15)", "point.E", HybridShapeRotateX, False)
        Call myFac.SelectAndBuildPoint2(pts(6), "FVertex:(Vertex:(Neighbours:(Face:(Brp:(G4Trap.1;(Brp:(G4Trap.1_GSMLoft.1;(Brp:(Sketch.1;1);Brp:(Sketch.1;2);Brp:(Sketch.1;3);Brp:(Sketch.1;4)))));None:();Cf11:());Face:(Brp:(G4Trap.1;(Brp:(G4Trap.1_GSMLoft.1;(Brp:(Sketch.1;3);Brp:(Sketch.2;3)))));None:();Cf11:());Face:(Brp:(G4Trap.1;(Brp:(G4Trap.1_GSMLoft.1;(Brp:(Sketch.1;2);Brp:(Sketch.2;2)))));None:();Cf11:()));Cf11:());WithPermanentBody;WithoutBuildError;WithSelectingFeatureSupport;MFBRepVersion_CXR15)", "point.E", HybridShapeRotateX, False)
        Call myFac.SelectAndBuildPoint2(pts(7), "FVertex:(Vertex:(Neighbours:(Face:(Brp:(G4Trap.1;(Brp:(G4Trap.1_GSMLoft.1;(Brp:(Sketch.1;2);Brp:(Sketch.2;2)))));None:();Cf11:());Face:(Brp:(G4Trap.1;(Brp:(G4Trap.1_GSMLoft.1;(Brp:(Sketch.1;1);Brp:(Sketch.1;2);Brp:(Sketch.1;3);Brp:(Sketch.1;4)))));None:();Cf11:());Face:(Brp:(G4Trap.1;(Brp:(G4Trap.1_GSMLoft.1;(Brp:(Sketch.1;1);Brp:(Sketch.2;1)))));None:();Cf11:()));Cf11:());WithPermanentBody;WithoutBuildError;WithSelectingFeatureSupport;MFBRepVersion_CXR15)", "point.G", HybridShapeRotateX, False)
        Call myFac.SelectAndBuildPoint2(pts(8), "FVertex:(Vertex:(Neighbours:(Face:(Brp:(G4Trap.1;(Brp:(G4Trap.1_GSMLoft.1;(Brp:(Sketch.1;1);Brp:(Sketch.2;1)))));None:();Cf11:());Face:(Brp:(G4Trap.1;(Brp:(G4Trap.1_GSMLoft.1;(Brp:(Sketch.1;1);Brp:(Sketch.1;2);Brp:(Sketch.1;3);Brp:(Sketch.1;4)))));None:();Cf11:());Face:(Brp:(G4Trap.1;(Brp:(G4Trap.1_GSMLoft.1;(Brp:(Sketch.1;4);Brp:(Sketch.2;4)))));None:();Cf11:()));Cf11:());WithPermanentBody;WithoutBuildError;WithSelectingFeatureSupport;MFBRepVersion_CXR15)", "point.H", HybridShapeRotateX, False)
        prt.Update

On Error GoTo NearErrorHandler
        Call prim.SetFactory(myFac)
        Call prim.SetPickedPoints2(pts)
        Call prim.BuildConstructPre
        Call prim.FixPointsOrder
        Call prim.BuildConstructPost
        Call prim.Recognize







        Call myFac.SelectShape2(sphInst)
        Call prim.ApplyParametersToUDF(sphInst)
    
        ' ---------------- Apply positioning ----------------
    
        Call myFac.SelectTranslate2(translFeature)
        ' Transformation matrix from global to local basis  (M1*M2*...)^1
        Call trMatrix.SetDimension(4)
        Call prTree.Init(translFeature)
        'Create M1*M2*... from tree
        Call prTree.createTransportMatrixToFinishPart(trMatrix)
        'Inverse M1*M2*... -> (M1*M2*...)^-1
        Call trMatrix.Inverse
        ' (M*) creation
        Call primitiveMat.SetDimension(4)
        Call prim.GetAxisSystem(primAxisSys)
        Call primitiveMat.EvaluateByAxisSys(primAxisSys)
        'M3 = ((M1*M2)^-1)*(M*)
        Call trMatrix.Multiply(primitiveMat)
        Call trMatrix.ExecuteTXYZ
        Call trMatrix.ApplyPosAndRotToFeature(translFeature)
        Call myFac.myUpdate
    
        Set prodDoc = CATIA.ActiveDocument
        Set sel = prodDoc.Selection
        sel.Clear
        Set prtDoc = docs.Item("Generic_trap_CAD.CATPart")
        Set prt = prtDoc.Part
        Set bodies = prt.bodies
        Set prtBody = bodies.Item("PartBody")
        sel.Add prtBody
        sel.Copy
        sel.Clear
    
        Set prtDoc = docs.Item("World.CATPart")
        Set prt = prtDoc.Part
        Set bodies = prt.bodies
        sel.Add prt
        sel.PasteSpecial "CATPrtResultWithOutLink"
        sel.Clear
        Set shpFactory = prt.ShapeFactory
        Set mBody = bodies.Item("Body.Fitted_trap.1")
        sel.Add mBody
        sel.Copy
        sel.Clear
    
        sel.Add prt
        sel.PasteSpecial "CATPrtResultWithOutLink"
        sel.Clear
        prt.Update
        Set mRemove = shpFactory.AddNewRemove(bodies.Item(bodies.Count - 1))
    
        On Error GoTo ErrHandler
        prt.Update
        formTrapScanner.Label1.Caption = "Result is not correct" & vbNewLine
        ListBox1.AddItem "[ER1] Parameters:   " & anglesString

        sel.Add bodies.Item(bodies.Count)
        sel.Delete

        myFac.Cleanup
        Call NextIter(mode)
        Exit Sub

ErrHandler:
        If (Err.Number = -2147467259 Or Err.Number = 0) Then
            formTrapScanner.Label1.Caption = "OK" & vbNewLine
            ListBox1.AddItem "[OK ] Parameters:   " & anglesString
            sel.Add bodies.Item(bodies.Count)
            sel.Delete
        Else
            MsgBox "Strange Error"
            ListBox1.AddItem "[ER3] Parameters:   " & anglesString
        End If

        myFac.Cleanup
        Call NextIter(mode)
        Exit Sub

NearErrorHandler:
        ListBox1.AddItem "[ER2] Parameters:   " & anglesString

        myFac.Cleanup
        Call NextIter(mode)
        Exit Sub

End Sub

Attribute VB_Name = "myAxisSystem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myAxisSystem class

Option Explicit

' -- Data members ----------------------------------------------------------------------

Dim mCenter(0 To 2) As Double

Dim mXort(0 To 2) As Double
Dim mYort(0 To 2) As Double
Dim mZort(0 To 2) As Double

' -- Methods ---------------------------------------------------------------------------

' OK
Public Sub SetXort(p_Xort() As Double)
    mXort(0) = p_Xort(0)
    mXort(1) = p_Xort(1)
    mXort(2) = p_Xort(2)
End Sub
Public Sub SetYort(p_Yort() As Double)
    mYort(0) = p_Yort(0)
    mYort(1) = p_Yort(1)
    mYort(2) = p_Yort(2)
End Sub
Public Sub SetZort(p_Zort() As Double)
    mZort(0) = p_Zort(0)
    mZort(1) = p_Zort(1)
    mZort(2) = p_Zort(2)
End Sub
Public Sub SetCenter(p_center() As Double)
    mCenter(0) = p_center(0)
    mCenter(1) = p_center(1)
    mCenter(2) = p_center(2)
End Sub

' OK
Public Sub GetXort(o_Xort() As Double)
    o_Xort(0) = mXort(0)
    o_Xort(1) = mXort(1)
    o_Xort(2) = mXort(2)
End Sub
Public Sub GetYort(o_Yort() As Double)
    o_Yort(0) = mYort(0)
    o_Yort(1) = mYort(1)
    o_Yort(2) = mYort(2)
End Sub
Public Sub GetZort(o_Zort() As Double)
    o_Zort(0) = mZort(0)
    o_Zort(1) = mZort(1)
    o_Zort(2) = mZort(2)
End Sub
Public Sub GetCenter(o_center() As Double)
    o_center(0) = mCenter(0)
    o_center(1) = mCenter(1)
    o_center(2) = mCenter(2)
End Sub

' OK
' Suppose that Yort and Zort are given, compute Xort using cross product
Public Sub ComputeXort()
    Me.CrossProduct mYort, mZort, mXort
End Sub

' OK
' Suppose that Zort and Xort are given, compute Yort using cross product
Public Sub ComputeYort()
    Me.CrossProduct mZort, mXort, mYort
End Sub

' OK
' Suppose that Xort and Yort are given, compute Zort using cross product
Public Sub ComputeZort()
    Me.CrossProduct mXort, mYort, mZort
End Sub

' OK
' c = [a;b]
' cx = ay*bz - az*by
' cy = az*bx - ax*bz
' cz = ax*by - ay*bx
Public Sub CrossProduct(p_op1() As Double, p_op2() As Double, o_res() As Double)
    o_res(0) = p_op1(1) * p_op2(2) - p_op1(2) * p_op2(1)
    o_res(1) = p_op1(2) * p_op2(0) - p_op1(0) * p_op2(2)
    o_res(2) = p_op1(0) * p_op2(1) - p_op1(1) * p_op2(0)
End Sub

' OK
'Public Sub Normalize(p_vector() As Double)
'    Dim v_length As Double
'    v_length = Sqrt(p_vector(0) ^ 2 + p_vector(1) ^ 2 + p_vector(2) ^ 2)
'    p_vector(0) = p_vector(0) / v_length
'    p_vector(1) = p_vector(1) / v_length
'    p_vector(2) = p_vector(2) / v_length
'End Sub

Public Sub Draw()

    MsgBox "X:" + Str(mXort(0)) + vbTab + Str(mXort(1)) + vbTab + Str(mXort(2)) + vbNewLine + _
        "Y:" + Str(mYort(0)) + vbTab + Str(mYort(1)) + vbTab + Str(mYort(2)) + vbNewLine + _
        "Z:" + Str(mZort(0)) + vbTab + Str(mZort(1)) + vbTab + Str(mZort(2))

End Sub

Attribute VB_Name = "myBox"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myBox class

Option Explicit

Const TOLERANCE = 10

' -- Data members ----------------------------------------------------------------------

Dim pickedPoints(1 To 8) As HybridShapePointCoord

' pointer to singleton myFactory object
Dim myFac As myFactory

' temporary construct element
Dim lines(1 To 7) As HybridShapeLinePtPt
Dim midPoints(1 To 7) As HybridShapePointBetween
Dim planes(1 To 2) As HybridShapePlane2Lines
Dim checkPlanes(1 To 4) As HybridShapePlane3Points
Dim Zaxis As HybridShapeLineNormal
Dim Xaxis As HybridShapeLineAngle
Dim Yaces(1 To 2) As HybridShapeLineAngle
Dim orientPlane As HybridShapePlane2Lines
Dim ZXplane As HybridShapePlane2Lines
Dim s As HybridShapeSphere
Dim Zorts As HybridShapeIntersection
Dim Xorts As HybridShapeIntersection
Dim Zort As HybridShape
Dim Xort As HybridShape
Dim Zort2 As HybridShape
Dim Xort2 As HybridShape

' recognized parameters
Dim pDx As Double
Dim pDy As Double
Dim pDz As Double

' recognized axis system
Dim mAxisSystem As New myAxisSystem

' -- Methods ---------------------------------------------------------------------------

Public Sub SetFactory(ByRef p_fac As myFactory)

    Set myFac = p_fac

End Sub

Public Sub SetPickedPoints(p_p1 As HybridShapePointCoord, p_p2 As HybridShapePointCoord, _
                            p_p3 As HybridShapePointCoord, p_p4 As HybridShapePointCoord, _
                            p_p5 As HybridShapePointCoord, p_p6 As HybridShapePointCoord, _
                            p_p7 As HybridShapePointCoord, p_p8 As HybridShapePointCoord)

    Set pickedPoints(1) = p_p1
    Set pickedPoints(2) = p_p2
    Set pickedPoints(3) = p_p3
    Set pickedPoints(4) = p_p4
    Set pickedPoints(5) = p_p5
    Set pickedPoints(6) = p_p6
    Set pickedPoints(7) = p_p7
    Set pickedPoints(8) = p_p8

End Sub

Public Sub SetPickedPoints2(p_pts() As HybridShapePointCoord)

    Me.SetPickedPoints p_pts(1), p_pts(2), p_pts(3), p_pts(4), p_pts(5), p_pts(6), p_pts(7), p_pts(8)

End Sub

Public Sub BuildConstructPre()

    myFac.BuildLine pickedPoints(1), pickedPoints(4), lines(1), "line.AD"
    myFac.BuildLine pickedPoints(2), pickedPoints(3), lines(2), "line.BC"
    myFac.BuildLine pickedPoints(5), pickedPoints(8), lines(3), "line.EH"
    myFac.BuildLine pickedPoints(6), pickedPoints(7), lines(4), "line.FG"

    ' Update
    myFac.myUpdate

End Sub

Public Sub FixPointsOrder()

    Dim tmpPoint As HybridShapePointCoord

    Dim coords1(2) As Variant
    Dim coords2(2) As Variant
    Dim mtrxData(2, 2) As Double

    Dim pointToGetCoords

    Set pointToGetCoords = pickedPoints(1)
    pointToGetCoords.GetCoordinates coords1

    Set pointToGetCoords = pickedPoints(4)
    pointToGetCoords.GetCoordinates coords2
    mtrxData(0, 0) = coords2(0) - coords1(0)        ' x    of vector 14
    mtrxData(0, 1) = coords2(1) - coords1(1)        ' y    of vector 14
    mtrxData(0, 2) = coords2(2) - coords1(2)        ' z    of vector 14

    Set pointToGetCoords = pickedPoints(2)
    pointToGetCoords.GetCoordinates coords2
    mtrxData(1, 0) = coords2(0) - coords1(0)        ' x    of vector 12
    mtrxData(1, 1) = coords2(1) - coords1(1)        ' y    of vector 12
    mtrxData(1, 2) = coords2(2) - coords1(2)        ' z    of vector 12

    Set pointToGetCoords = pickedPoints(5)
    pointToGetCoords.GetCoordinates coords2
    mtrxData(2, 0) = coords2(0) - coords1(0)        ' x    of vector 15
    mtrxData(2, 1) = coords2(1) - coords1(1)        ' y    of vector 15
    mtrxData(2, 2) = coords2(2) - coords1(2)        ' z    of vector 15

    Dim tmpM As New Matrix
    tmpM.SetDimension 3
    tmpM.SetData mtrxData

    If (tmpM.Det < 0) Then

        ' Remove wrong lines and planes
        myFac.RemovePreConstruct lines(1)
        myFac.RemovePreConstruct lines(2)
        myFac.RemovePreConstruct lines(3)
        myFac.RemovePreConstruct lines(4)

        ' exchange 2 <-> 4 and 6 <-> 8
        'MsgBox "swap2"
        Set tmpPoint = pickedPoints(2)
        Set pickedPoints(2) = pickedPoints(4)
        Set pickedPoints(4) = tmpPoint
        Set tmpPoint = pickedPoints(6)
        Set pickedPoints(6) = pickedPoints(8)
        Set pickedPoints(8) = tmpPoint

        ' Construct new lines and planes
        BuildConstructPre

    End If

End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8
    myFac.BuildPlane3Pt pickedPoints(2), pickedPoints(3), pickedPoints(6), checkPlanes(3), "plane.3.check" '7
    myFac.BuildPlane3Pt pickedPoints(1), pickedPoints(4), pickedPoints(5), checkPlanes(4), "plane.4.check" '8

    ' Update
    myFac.myUpdate

    ' Check planarity of some faces
    formPrimitiveCreator.TextBox2.Text = myFac.GetDistance(checkPlanes(1), pickedPoints(4))
    formPrimitiveCreator.TextBox3.Text = myFac.GetDistance(checkPlanes(2), pickedPoints(8))
    formPrimitiveCreator.TextBox4.Text = myFac.GetDistance(checkPlanes(3), pickedPoints(7))
    formPrimitiveCreator.TextBox5.Text = myFac.GetDistance(checkPlanes(4), pickedPoints(8))

    ' Build all the middle points and lines, connecting them
    myFac.BuildMidPoint2 pickedPoints(1), pickedPoints(4), midPoints(1), "point.mid.1"
    myFac.BuildMidPoint2 pickedPoints(2), pickedPoints(3), midPoints(2), "point.mid.2"
    myFac.BuildMidPoint2 pickedPoints(5), pickedPoints(8), midPoints(3), "point.mid.3"
    myFac.BuildMidPoint2 pickedPoints(6), pickedPoints(7), midPoints(4), "point.mid.4"
    myFac.BuildLine midPoints(1), midPoints(2), lines(5), "line.bottom.mid"
    myFac.BuildLine midPoints(3), midPoints(4), lines(6), "line.top.mid"
    myFac.BuildMidPoint2 midPoints(1), midPoints(2), midPoints(5), "point.mid.5"
    myFac.BuildMidPoint2 midPoints(3), midPoints(4), midPoints(6), "point.mid.6"
    myFac.BuildLine midPoints(5), midPoints(6), lines(7), "line.mid"
    myFac.BuildMidPoint2 midPoints(5), midPoints(6), midPoints(7), "point.center"
    myFac.myUpdate

    ' Build top and botton planes
    myFac.BuildPlane lines(1), lines(2), planes(1), "plane.bottom"
    myFac.BuildPlane lines(3), lines(4), planes(2), "plane.top"

    ' Build Y axis in both planes
    myFac.BuildNormalToLine lines(1), planes(1), midPoints(1), Yaces(1), "line.bottom.Y"
    myFac.BuildNormalToLine lines(3), planes(2), midPoints(3), Yaces(2), "line.top.Y"

    ' Build X axis of the primitive
    myFac.BuildParallelLine lines(1), planes(1), midPoints(7), Xaxis, "XaxisOfThePrimitive"

    ' Build Z axis of the primitive
    myFac.BuildNormalToPlane planes(1), midPoints(7), Zaxis, "ZaxisOfThePrimitive"
    
    ' Update
    myFac.myUpdate

    myFac.BuildSphere midPoints(7), 1#, s, "sphere.identity"
    myFac.BuildIntersection s, Zaxis, Zorts, "Zorts"
    myFac.BuildIntersection s, Xaxis, Xorts, "Xorts"

    Dim lineCD As HybridShapeLinePtPt
    myFac.BuildLine pickedPoints(3), pickedPoints(4), lineCD, "line.CD"

    myFac.SelectNearestPoint Zorts, planes(2), Zort, "Zort"
    myFac.SelectNearestPoint Xorts, lineCD, Xort, "Xort"
    myFac.BuildPoint Zort, Zort2, "Zort2"
    myFac.BuildPoint Xort, Xort2, "Xort2"

    ' Update
    myFac.myUpdate

    ' Extract axis system of the primitve

    Dim v_pointToExtractCoordinates
    Dim v_tmpVariant(2)
    Dim v_tmpDouble(2) As Double
    Dim v_tmpCenter(2) As Double

    Set v_pointToExtractCoordinates = midPoints(7)
    v_pointToExtractCoordinates.GetCoordinates v_tmpVariant
    v_tmpCenter(0) = v_tmpVariant(0)
    v_tmpCenter(1) = v_tmpVariant(1)
    v_tmpCenter(2) = v_tmpVariant(2)
    mAxisSystem.SetCenter v_tmpCenter    ' Set center of the axis system

    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Z direction of the axis system

    Set v_pointToExtractCoordinates = Xort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetXort v_tmpDouble      ' Set X direction of the axis system

    mAxisSystem.ComputeYort              ' Compute the last Y direction from given Z and X directions

    'Call mAxisSystem.Draw

End Sub

Public Sub Recognize()

    ' Extract parameters of the primitive

    pDx = Round(myFac.GetDistance(pickedPoints(1), pickedPoints(4)) / 2#, TOLERANCE)
    pDy = Round(myFac.GetDistance(pickedPoints(1), pickedPoints(2)) / 2#, TOLERANCE)
    pDz = Round(myFac.GetDistance(pickedPoints(1), pickedPoints(5)) / 2#, TOLERANCE)

    formPrimitiveCreator.ListBox1.AddItem "pDx = " & Trim(Str(pDx))
    formPrimitiveCreator.ListBox1.AddItem "pDy = " & Trim(Str(pDy))
    formPrimitiveCreator.ListBox1.AddItem "pDz = " & Trim(Str(pDz))

End Sub

Public Sub ApplyParametersToUDF(shpInst As ShapeInstance)
    Call shpInst.GetParameter("pX").ValuateFromString(Trim(Str(pDx)) + "mm")
    Call shpInst.GetParameter("pY").ValuateFromString(Trim(Str(pDy)) + "mm")
    Call shpInst.GetParameter("pZ").ValuateFromString(Trim(Str(pDz)) + "mm")
End Sub

Public Sub GetAxisSystem(ByRef o_axSystem As myAxisSystem)
    Set o_axSystem = mAxisSystem
End Sub

Attribute VB_Name = "myFactory"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myFactory class

Option Explicit

Const PI = 3.14159265358979

Dim prt As Part
Dim sel
Dim mFactory As HybridShapeFactory
Dim mGeomSet As HybridBody
Dim AFormMethodIsBeingExecuted As Boolean
Dim TheSPAWorkbench As Workbench

Public Sub Init()
    Dim prtDoc As PartDocument
    Dim prodDoc As ProductDocument
    If TypeName(CATIA.ActiveDocument) = "PartDocument" Then
        Set prtDoc = CATIA.ActiveDocument
        Set sel = prtDoc.Selection
        Set prt = prtDoc.Part
        Set mFactory = prt.HybridShapeFactory
        Set mGeomSet = prt.HybridBodies.Add()
        mGeomSet.Name = "Primitive_construct"
        Set TheSPAWorkbench = prtDoc.GetWorkbench("SPAWorkbench")
    ElseIf TypeName(CATIA.ActiveDocument) = "ProductDocument" Then
        Set prodDoc = CATIA.ActiveDocument
        Set sel = prodDoc.Selection
    End If
End Sub

Public Sub SelectAndBuildPoint(pt As HybridShapePointCoord, list As ListBox, givenName As String, firstPoint As Boolean)
    Dim inpObjType_vertex(0)
    inpObjType_vertex(0) = "Vertex"
    Dim stat
    sel.Clear
    AFormMethodIsBeingExecuted = True
    stat = sel.SelectElement2(inpObjType_vertex, "Select a vertex", False)
    AFormMethodIsBeingExecuted = False
    If (stat = "Normal") Then
        Dim selectedPoint1
        Set selectedPoint1 = sel.Item2(1).Value

        If (firstPoint = True) Then
                Dim selEl As SelectedElement
                Dim selElProd As Product
                Dim prtDoc As PartDocument
                Set selEl = sel.Item2(1)
                Set selElProd = selEl.LeafProduct
                Set prtDoc = selElProd.ReferenceProduct.Parent
                
                ' Factory initialization (second step)
                Set prt = prtDoc.Part
                Set mFactory = prt.HybridShapeFactory
                Set mGeomSet = prt.HybridBodies.Add()
                mGeomSet.Name = "Primitive_construct"
                Set TheSPAWorkbench = prtDoc.GetWorkbench("SPAWorkbench")
        End If

        Set pt = mFactory.AddNewPointCoordWithReference(0#, 0#, 0#, selectedPoint1)
        pt.Name = givenName
        mGeomSet.AppendHybridShape pt
        list.AddItem givenName
    Else
        End
    End If
End Sub

Public Sub Init2()
        Dim docs As Documents
        Dim prtDoc As PartDocument
        Dim prodDoc As ProductDocument
        Set prodDoc = CATIA.ActiveDocument
        Set sel = prodDoc.Selection
        Set docs = CATIA.Documents
        Set prtDoc = docs.Item("Generic_trap_CAD.CATPart")
        ' Factory initialization (second step)
        Set prt = prtDoc.Part
        
        Set mFactory = prt.HybridShapeFactory
        'Set mGeomSet = prt.HybridBodies.Add()
        'mGeomSet.Name = "Primitive_construct"
        'Set TheSPAWorkbench = prtDoc.GetWorkbench("SPAWorkbench")
End Sub

Public Sub SelectAndBuildPoint2(pt As HybridShapePointCoord, iLabel As String, givenName As String, shps As HybridShapeRotate, firstPoint As Boolean)
    Dim docs As Documents
    Dim prtDoc As PartDocument
    Dim prt As Part
    
    sel.Clear
    Dim refs(7) As Reference
    Set docs = CATIA.Documents
    Set prtDoc = docs.Item("Generic_trap_CAD.CATPart")
    Set prt = prtDoc.Part

    If (firstPoint = True) Then
        ' Factory initialization (second step)
        Set prt = prtDoc.Part
        Set mFactory = prt.HybridShapeFactory
        Set mGeomSet = prt.HybridBodies.Add()
        mGeomSet.Name = "Primitive_construct"
        Set TheSPAWorkbench = prtDoc.GetWorkbench("SPAWorkbench")
    End If

    Set refs(0) = prt.CreateReferenceFromBRepName(iLabel, shps)
    Set pt = mFactory.AddNewPointCoordWithReference(0#, 0#, 0#, refs(0))
    pt.Name = givenName
    mGeomSet.AppendHybridShape pt
End Sub

Public Sub SelectShape2(o_sphInst As ShapeInstance)
    Dim docs As Documents
    Dim prtDoc As PartDocument
    Dim prt As Part
    Dim prtBody As Body
    Dim shps As Shapes
    'Dim targBody As Body
    'Dim shapeInstance1 As HybridShapeTranslate
    
    Set docs = CATIA.Documents
    Set prtDoc = docs.Item("Fitted_trap.CATPart")
    Set prt = prtDoc.Part
    Set prtBody = prt.MainBody
    'Set targBody = prt.Bodies.Item(2)
    Set shps = prtBody.Shapes
    Set o_sphInst = shps.Item("G4Trap.1")
End Sub

Public Sub SelectTranslate2(trans As HybridShapeTranslate)
    Dim docs As Documents
    Dim prtDoc As PartDocument
    Dim prt As Part
    Dim prtBody As Body
    Dim shps As Shapes
    Dim targBody As Body
    'Dim shapeInstance1 As HybridShapeTranslate
    
    Set docs = CATIA.Documents
    Set prtDoc = docs.Item("World.CATPart")
    Set prt = prtDoc.Part
    'Set prtBody = prt.MainBody
    Set targBody = prt.bodies.Item(2)
    Set shps = targBody.Shapes
    Set trans = shps.Item("Translate.1")
End Sub

' --------------------------------------------------------------------------------------------------------------------

Public Sub BuildPoint(p_pt As HybridShape, _
                        o_pt As HybridShape, _
                        p_givenName As String)
    Set o_pt = mFactory.AddNewPointCoordWithReference(0#, 0#, 0#, p_pt)
    If (p_givenName <> "") Then o_pt.Name = p_givenName
    mGeomSet.AppendHybridShape o_pt
End Sub

Public Sub BuildPoint2(p_line As HybridShape, _
                        p_refpt As HybridShape, _
                        o_pt As HybridShape, _
                        p_givenName As String)
    Set o_pt = mFactory.AddNewPointOnCurveWithReferenceFromDistance(p_line, p_refpt, 1#, False)
    If (p_givenName <> "") Then o_pt.Name = p_givenName
    mGeomSet.AppendHybridShape o_pt
End Sub

Public Sub BuildLine(p_pt1 As HybridShape, _
                        p_pt2 As HybridShape, _
                        o_line As HybridShapeLinePtPt, _
                        p_givenName As String)
    Set o_line = mFactory.AddNewLinePtPt(p_pt1, p_pt2)
    If (p_givenName <> "") Then o_line.Name = p_givenName
    mGeomSet.AppendHybridShape o_line
End Sub

Public Sub BuildPlane(p_lin1 As HybridShape, _
                        p_lin2 As HybridShape, _
                        o_pl As HybridShapePlane2Lines, _
                        p_givenName As String)
    Set o_pl = mFactory.AddNewPlane2Lines(p_lin1, p_lin2)
    If (p_givenName <> "") Then o_pl.Name = p_givenName
    mGeomSet.AppendHybridShape o_pl
End Sub

Public Sub BuildIntersectionPoint(p_lin1 As HybridShape, _
                                    p_lin2 As HybridShape, _
                                    o_pt As HybridShape, _
                                    p_givenName As String)
    Set o_pt = mFactory.AddNewIntersection(p_lin1, p_lin2)
    If (p_givenName <> "") Then o_pt.Name = p_givenName
    o_pt.ExtendMode = 3
    mGeomSet.AppendHybridShape o_pt
End Sub

'Public Sub BuildMidPoint(p_lin As HybridShape, _
'                            o_pt As HybridShape, _
'                            p_givenName As String)
'    Set o_pt = mFactory.AddNewPointOnCurveFromPercent(p_lin, 0.5, False)
'    If (p_givenName <> "") Then o_pt.Name = p_givenName
'    mGeomSet.AppendHybridShape o_pt
'End Sub

Public Sub BuildMidPoint2(p_pt1 As HybridShape, _
                            p_pt2 As HybridShape, _
                            o_pt As HybridShape, _
                            p_givenName As String)
    Set o_pt = mFactory.AddNewPointBetween(p_pt1, p_pt2, 0.5, 0)
    If (p_givenName <> "") Then o_pt.Name = p_givenName
    mGeomSet.AppendHybridShape o_pt
End Sub

Public Sub BuildPlane3Pt(p_pt1 As HybridShape, _
                        p_pt2 As HybridShape, _
                        p_pt3 As HybridShape, _
                        o_pl As HybridShape, _
                        p_givenName As String)
    Set o_pl = mFactory.AddNewPlane3Points(p_pt1, p_pt2, p_pt3)
    If (p_givenName <> "") Then o_pl.Name = p_givenName
    mGeomSet.AppendHybridShape o_pl
End Sub

Public Sub BuildIntersectionLine(p_pl1 As HybridShape, _
                                    p_pl2 As HybridShape, _
                                    o_lin As HybridShape, _
                                    p_givenName As String)
    Set o_lin = mFactory.AddNewIntersection(p_pl1, p_pl2)
    If (p_givenName <> "") Then o_lin.Name = p_givenName
    mGeomSet.AppendHybridShape o_lin
End Sub

Public Sub BuildNormalToLine(p_lin1 As HybridShape, _
                        p_pl As HybridShape, _
                        p_pt As HybridShape, _
                        o_lin As HybridShape, _
                        p_givenName As String)
    Set o_lin = mFactory.AddNewLineAngle(p_lin1, p_pl, p_pt, False, 0#, 3000#, 90#, True)
    If (p_givenName <> "") Then o_lin.Name = p_givenName
    mGeomSet.AppendHybridShape o_lin
End Sub

Public Sub BuildParallelLine(p_lin1 As HybridShape, _
                        p_pl As HybridShape, _
                        p_pt As HybridShape, _
                        o_lin As HybridShape, _
                        p_givenName As String)
    Set o_lin = mFactory.AddNewLineAngle(p_lin1, p_pl, p_pt, False, 0#, 3000#, 0#, True)
    o_lin.SetLengthType 1
    If (p_givenName <> "") Then o_lin.Name = p_givenName
    mGeomSet.AppendHybridShape o_lin
End Sub

Public Sub BuildNormalToPlane(p_pl As HybridShape, _
                        p_pt As HybridShape, _
                        o_lin As HybridShape, _
                        p_givenName As String)
    Set o_lin = mFactory.AddNewLineNormal(p_pl, p_pt, 0#, 3000#, True)
    o_lin.SetLengthType 1
    If (p_givenName <> "") Then o_lin.Name = p_givenName
    mGeomSet.AppendHybridShape o_lin
End Sub

' --------------------------------------------------------------------------------------------------------------------

Public Sub BuildSphere(pt As HybridShape, _
                        r As Double, _
                        s As HybridShapeSphere, _
                        givenName As String)
    Set s = mFactory.AddNewSphere(pt, Nothing, r, -90#, 90#, 0#, 360#)
    s.Name = givenName
    mGeomSet.AppendHybridShape s
End Sub

Public Sub BuildIntersection(shp1 As HybridShape, _
                                shp2 As HybridShape, _
                                res As HybridShape, _
                                givenName As String)
    Set res = mFactory.AddNewIntersection(shp1, shp2)
    res.Name = givenName
    mGeomSet.AppendHybridShape res
End Sub

Public Sub SelectNearestPoint(mult As HybridShape, _
                                refer As HybridShape, _
                                res As HybridShape, _
                                givenName As String)
    ' Why?
    If (TypeName(refer) = "HybridShapeLinePtPt") Then
        refer.SetLengthType 0
    End If

    Set res = mFactory.AddNewNear(mult, refer)
    res.Name = givenName
    mGeomSet.AppendHybridShape res
End Sub

Public Sub SelectShape(o_sphInst As ShapeInstance)
    Dim inpObjType_shape(0)
    inpObjType_shape(0) = "Shape"
    Dim stat
    sel.Clear
    AFormMethodIsBeingExecuted = True
    stat = sel.SelectElement2(inpObjType_shape, "Select the UDF feature", False)
    AFormMethodIsBeingExecuted = False
    If (stat = "Normal") Then
        Set o_sphInst = sel.Item2(1).Value
    Else
        End
    End If
End Sub

Public Sub SelectTranslate(trans As HybridShapeTranslate)
    Dim inpObjType_tridim(0)
    inpObjType_tridim(0) = "TriDim"
    Dim stat
    sel.Clear
    AFormMethodIsBeingExecuted = True
    stat = sel.SelectElement2(inpObjType_tridim, "Select the translation feature", False)
    AFormMethodIsBeingExecuted = False
    If (stat = "Normal") Then
        Set trans = sel.Item2(1).Value
    Else
        End
    End If
End Sub

' --------------------------------------------------------------------------------------------------------------------

Public Function GetDistance(pt1 As HybridShape, pt2 As HybridShape) As Double

    If (TypeName(pt1) = "HybridShapeLinePtPt" And TypeName(pt2) = "HybridShapeLinePtPt") Then
        Dim lenType1 As Long
        Dim lenType2 As Long
        lenType1 = pt1.GetLengthType
        lenType2 = pt2.GetLengthType
        If (lenType1 <> 1) Then
            pt1.SetLengthType (1)
        End If
        If (lenType2 <> 1) Then
            pt2.SetLengthType (1)
        End If
        Me.myUpdate
    End If

    Dim ref1 As Reference
    Dim ref2 As Reference
    Set ref1 = prt.CreateReferenceFromObject(pt1)
    Set ref2 = prt.CreateReferenceFromObject(pt2)
    Dim Measure1  As Measurable
    Set Measure1 = TheSPAWorkbench.GetMeasurable(ref1)
    GetDistance = Measure1.GetMinimumDistance(ref2)

    If (TypeName(pt1) = "HybridShapeLinePtPt" And TypeName(pt2) = "HybridShapeLinePtPt") Then
        pt1.SetLengthType (lenType1)
        pt2.SetLengthType (lenType2)
        Me.myUpdate
    End If

End Function

Public Function GetAngle(lin1 As HybridShape, lin2 As HybridShape) As Double
    Dim ref1 As Reference
    Dim ref2 As Reference
    Set ref1 = prt.CreateReferenceFromObject(lin1)
    Set ref2 = prt.CreateReferenceFromObject(lin2)
    Dim Measure1  As Measurable
    Set Measure1 = TheSPAWorkbench.GetMeasurable(ref1)
    GetAngle = Measure1.GetAngleBetween(ref2)
End Function

Public Sub Center(cent As HybridShape, var() As Double)
'    If formTrapCreator.chkRoundPosRot.Value = True Then
  Dim m ' as measurable
  Dim v(2)
  Set m = TheSPAWorkbench.GetMeasurable(cent)
  m.GetPoint v
  var(0) = v(0)
  var(1) = v(1)
  var(2) = v(2)
End Sub

' What the hell?
'Public Sub GetStandartPlaneZX(Plane As Object)
'    Dim OriginElements
'    Set OriginElements = prt.OriginElements
'    Set Plane = OriginElements.PlaneZX
'End Sub

Public Sub RemovePreConstruct(obj As HybridShape)
    sel.Clear
    sel.Add obj
    sel.Delete
    sel.Clear
End Sub

Public Sub Cleanup()
    sel.Clear
    sel.Add mGeomSet
    sel.Delete
End Sub

Public Sub myUpdate()
    Dim prtDoc As PartDocument
    Dim prodDoc As ProductDocument
    Dim prt2 As Part
    Dim prod As Product
    If TypeName(CATIA.ActiveDocument) = "PartDocument" Then
        Set prtDoc = CATIA.ActiveDocument
        Set prt2 = prtDoc.Part
        prt2.Update
    ElseIf TypeName(CATIA.ActiveDocument) = "ProductDocument" Then
        Set prodDoc = CATIA.ActiveDocument
        Set prod = prodDoc.Product
        prod.Update
    End If
End Sub

Attribute VB_Name = "myPara"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myPara class

Option Explicit

Const TOLERANCE = 10

' -- Data members ----------------------------------------------------------------------

Dim pickedPoints(1 To 8) As HybridShapePointCoord

' pointer to singleton myFactory object
Dim myFac As myFactory

' temporary construct element
Dim lines(1 To 7) As HybridShapeLinePtPt
Dim midPoints(1 To 7) As HybridShapePointBetween
Dim planes(1 To 2) As HybridShapePlane2Lines
Dim checkPlanes(1 To 4) As HybridShapePlane3Points
Dim Zaxis As HybridShapeLineNormal
Dim Xaxis As HybridShapeLineAngle
Dim Yaces(1 To 2) As HybridShapeLineAngle
Dim orientPlane As HybridShapePlane2Lines
Dim ZXplane As HybridShapePlane2Lines

Dim s As HybridShapeSphere
Dim Zorts As HybridShapeIntersection
Dim Xorts As HybridShapeIntersection
Dim Zort As HybridShape
Dim Xort As HybridShape
Dim Zort2 As HybridShape
Dim Xort2 As HybridShape

' recognized parameters

Dim pDy As Double
Dim pDx As Double
Dim pDz As Double
Dim pAlpha As Double
Dim pTheta As Double
Dim pPhi As Double

' recognized axis system
Dim mAxisSystem As New myAxisSystem

' -- Methods ---------------------------------------------------------------------------

Public Sub SetFactory(ByRef p_fac As myFactory)

    Set myFac = p_fac

End Sub

Public Sub SetPickedPoints(p_p1 As HybridShapePointCoord, p_p2 As HybridShapePointCoord, _
                            p_p3 As HybridShapePointCoord, p_p4 As HybridShapePointCoord, _
                            p_p5 As HybridShapePointCoord, p_p6 As HybridShapePointCoord, _
                            p_p7 As HybridShapePointCoord, p_p8 As HybridShapePointCoord)

    Set pickedPoints(1) = p_p1
    Set pickedPoints(2) = p_p2
    Set pickedPoints(3) = p_p3
    Set pickedPoints(4) = p_p4
    Set pickedPoints(5) = p_p5
    Set pickedPoints(6) = p_p6
    Set pickedPoints(7) = p_p7
    Set pickedPoints(8) = p_p8

End Sub

Public Sub SetPickedPoints2(p_pts() As HybridShapePointCoord)

    Me.SetPickedPoints p_pts(1), p_pts(2), p_pts(3), p_pts(4), p_pts(5), p_pts(6), p_pts(7), p_pts(8)

End Sub

Public Sub BuildConstructPre()

    myFac.BuildLine pickedPoints(1), pickedPoints(4), lines(1), "line.AD"
    myFac.BuildLine pickedPoints(2), pickedPoints(3), lines(2), "line.BC"
    myFac.BuildLine pickedPoints(5), pickedPoints(8), lines(3), "line.EH"
    myFac.BuildLine pickedPoints(6), pickedPoints(7), lines(4), "line.FG"

    ' Update
    myFac.myUpdate

End Sub

Public Sub FixPointsOrder()

    Dim tmpPoint As HybridShapePointCoord

    Dim coords1(2) As Variant
    Dim coords2(2) As Variant
    Dim mtrxData(2, 2) As Double

    Dim pointToGetCoords

    Set pointToGetCoords = pickedPoints(1)
    pointToGetCoords.GetCoordinates coords1

    Set pointToGetCoords = pickedPoints(4)
    pointToGetCoords.GetCoordinates coords2
    mtrxData(0, 0) = coords2(0) - coords1(0)        ' x    of vector 14
    mtrxData(0, 1) = coords2(1) - coords1(1)        ' y    of vector 14
    mtrxData(0, 2) = coords2(2) - coords1(2)        ' z    of vector 14

    Set pointToGetCoords = pickedPoints(2)
    pointToGetCoords.GetCoordinates coords2
    mtrxData(1, 0) = coords2(0) - coords1(0)        ' x    of vector 12
    mtrxData(1, 1) = coords2(1) - coords1(1)        ' y    of vector 12
    mtrxData(1, 2) = coords2(2) - coords1(2)        ' z    of vector 12

    Set pointToGetCoords = pickedPoints(5)
    pointToGetCoords.GetCoordinates coords2
    mtrxData(2, 0) = coords2(0) - coords1(0)        ' x    of vector 15
    mtrxData(2, 1) = coords2(1) - coords1(1)        ' y    of vector 15
    mtrxData(2, 2) = coords2(2) - coords1(2)        ' z    of vector 15

    Dim tmpM As New Matrix
    tmpM.SetDimension 3
    tmpM.SetData mtrxData

    If (tmpM.Det < 0) Then

        ' Remove wrong lines and planes
        myFac.RemovePreConstruct lines(1)
        myFac.RemovePreConstruct lines(2)
        myFac.RemovePreConstruct lines(3)
        myFac.RemovePreConstruct lines(4)

        ' exchange 2 <-> 4 and 6 <-> 8
        'MsgBox "swap2"
        Set tmpPoint = pickedPoints(2)
        Set pickedPoints(2) = pickedPoints(4)
        Set pickedPoints(4) = tmpPoint
        Set tmpPoint = pickedPoints(6)
        Set pickedPoints(6) = pickedPoints(8)
        Set pickedPoints(8) = tmpPoint

        ' Construct new lines and planes
        BuildConstructPre

    End If

    
End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8
    myFac.BuildPlane3Pt pickedPoints(2), pickedPoints(3), pickedPoints(6), checkPlanes(3), "plane.3.check" '7
    myFac.BuildPlane3Pt pickedPoints(1), pickedPoints(4), pickedPoints(5), checkPlanes(4), "plane.4.check" '8

    ' Update
    myFac.myUpdate

    ' Check planarity of some faces
    formPrimitiveCreator.TextBox2.Text = myFac.GetDistance(checkPlanes(1), pickedPoints(4))
    formPrimitiveCreator.TextBox3.Text = myFac.GetDistance(checkPlanes(2), pickedPoints(8))
    formPrimitiveCreator.TextBox4.Text = myFac.GetDistance(checkPlanes(3), pickedPoints(7))
    formPrimitiveCreator.TextBox5.Text = myFac.GetDistance(checkPlanes(4), pickedPoints(8))

    ' Build all the middle points and lines, connecting them
    myFac.BuildMidPoint2 pickedPoints(1), pickedPoints(4), midPoints(1), "point.mid.1"
    myFac.BuildMidPoint2 pickedPoints(2), pickedPoints(3), midPoints(2), "point.mid.2"
    myFac.BuildMidPoint2 pickedPoints(5), pickedPoints(8), midPoints(3), "point.mid.3"
    myFac.BuildMidPoint2 pickedPoints(6), pickedPoints(7), midPoints(4), "point.mid.4"
    myFac.BuildLine midPoints(1), midPoints(2), lines(5), "line.bottom.mid"
    myFac.BuildLine midPoints(3), midPoints(4), lines(6), "line.top.mid"
    myFac.BuildMidPoint2 midPoints(1), midPoints(2), midPoints(5), "point.mid.5"
    myFac.BuildMidPoint2 midPoints(3), midPoints(4), midPoints(6), "point.mid.6"
    myFac.BuildLine midPoints(5), midPoints(6), lines(7), "line.mid"
    myFac.BuildMidPoint2 midPoints(5), midPoints(6), midPoints(7), "point.center"

    ' Build top and botton planes
    myFac.BuildPlane lines(1), lines(2), planes(1), "plane.bottom"
    myFac.BuildPlane lines(3), lines(4), planes(2), "plane.top"

    ' Build Y axis in both planes
    myFac.BuildNormalToLine lines(1), planes(1), midPoints(1), Yaces(1), "line.bottom.Y"
    myFac.BuildNormalToLine lines(3), planes(2), midPoints(3), Yaces(2), "line.top.Y"

    ' Build X axis of the primitive
    myFac.BuildParallelLine lines(1), planes(1), midPoints(7), Xaxis, "XaxisOfThePrimitive"

    ' Build Z axis of the primitive
    myFac.BuildNormalToPlane planes(1), midPoints(7), Zaxis, "ZaxisOfThePrimitive"

    
    ' Update
    myFac.myUpdate

    ' if Z axis of the primitive does not coincide with the middle line of the primitive
    If (Round(myFac.GetAngle(lines(7), Zaxis), TOLERANCE) <> 0 And _
        Round(myFac.GetAngle(lines(7), Zaxis), TOLERANCE) <> 180) Then

        ' Build the plane through the Z axis and the middle line of the primitive
        myFac.BuildPlane lines(7), Zaxis, orientPlane, "plane.orientation"
    
        ' Build ZX plane of the primitive
        myFac.BuildPlane Zaxis, Xaxis, ZXplane, "plane.ZX"

    End If

    myFac.BuildSphere midPoints(7), 1#, s, "sphere.identity"
    myFac.BuildIntersection s, Zaxis, Zorts, "Zorts"
    myFac.BuildIntersection s, Xaxis, Xorts, "Xorts"

    Dim lineCD As HybridShapeLinePtPt
    myFac.BuildLine pickedPoints(3), pickedPoints(4), lineCD, "line.CD"

    myFac.SelectNearestPoint Zorts, planes(2), Zort, "Zort"
    myFac.SelectNearestPoint Xorts, lineCD, Xort, "Xort"
    myFac.BuildPoint Zort, Zort2, "Zort2"
    myFac.BuildPoint Xort, Xort2, "Xort2"

    ' Update
    myFac.myUpdate

    ' Extract axis system of the primitve

    Dim v_pointToExtractCoordinates
    Dim v_tmpVariant(2)
    Dim v_tmpDouble(2) As Double
    Dim v_tmpCenter(2) As Double

    Set v_pointToExtractCoordinates = midPoints(7)
    v_pointToExtractCoordinates.GetCoordinates v_tmpVariant
    v_tmpCenter(0) = v_tmpVariant(0)
    v_tmpCenter(1) = v_tmpVariant(1)
    v_tmpCenter(2) = v_tmpVariant(2)
    mAxisSystem.SetCenter v_tmpCenter    ' Set center of the axis system

    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Z direction of the axis system

    Set v_pointToExtractCoordinates = Xort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetXort v_tmpDouble      ' Set X direction of the axis system

    mAxisSystem.ComputeYort              ' Compute the last Y direction from given Z and X directions

    'Call mAxisSystem.Draw

End Sub

Public Sub Recognize()

    ' Extract parameters of the primitive

    pDz = Round(myFac.GetDistance(planes(1), planes(2)) / 2#, TOLERANCE)

    ' if Z axis of the primitive does not coincide with the middle line of the primitive
    If (Round(myFac.GetAngle(lines(7), Zaxis), TOLERANCE) <> 0 And _
        Round(myFac.GetAngle(lines(7), Zaxis), TOLERANCE) <> 180) Then
        pTheta = Round(myFac.GetAngle(orientPlane, ZXplane), TOLERANCE) 'поменять местами вычисления для Theta и Phi!!!
        pPhi = Round(myFac.GetAngle(Zaxis, lines(7)), TOLERANCE)
        Call ImprovePhi
    Else
        pTheta = 0
        pPhi = 0
    End If

    pDy = Round(myFac.GetDistance(lines(1), lines(2)) / 2#, TOLERANCE)
    pDx = Round(myFac.GetDistance(pickedPoints(1), pickedPoints(4)) / 2#, TOLERANCE)
    pAlpha = Round(myFac.GetAngle(Yaces(1), lines(5)), TOLERANCE)

    ' alpha improvement
    If (pAlpha <> 0) Then
        If (myFac.GetDistance(pickedPoints(1), midPoints(2)) < myFac.GetDistance(pickedPoints(4), midPoints(2))) Then
            pAlpha = -pAlpha
        End If
    End If

    formPrimitiveCreator.ListBox1.AddItem "dx = " & Trim(Str(pDx))
    formPrimitiveCreator.ListBox1.AddItem "dy = " & Trim(Str(pDy))
    formPrimitiveCreator.ListBox1.AddItem "dz = " & Trim(Str(pDz))
    formPrimitiveCreator.ListBox1.AddItem "alpha = " & Trim(Str(pAlpha))
    formPrimitiveCreator.ListBox1.AddItem "theta = " & Trim(Str(pTheta))
    formPrimitiveCreator.ListBox1.AddItem "phi = " & Trim(Str(pPhi))

End Sub

Public Sub ApplyParametersToUDF(shpInst As ShapeInstance)

    Call shpInst.GetParameter("dx").ValuateFromString(Trim(Str(pDx)) + "mm")
    Call shpInst.GetParameter("dy").ValuateFromString(Trim(Str(pDy)) + "mm")
    Call shpInst.GetParameter("dz").ValuateFromString(Trim(Str(pDz)) + "mm")
    Call shpInst.GetParameter("alpha").ValuateFromString(Trim(Str(pAlpha)) + "deg")
    Call shpInst.GetParameter("theta").ValuateFromString(Trim(Str(pTheta)) + "deg")
    Call shpInst.GetParameter("phi").ValuateFromString(Trim(Str(pPhi)) + "deg")
End Sub

Public Sub GetAxisSystem(ByRef o_axSystem As myAxisSystem)
    Set o_axSystem = mAxisSystem
End Sub

Public Sub ImprovePhi()

    Dim mtrxData(2, 2) As Double
    Dim tmpData(2) As Double

    Dim pointToGetCoords
    Dim coords1(2) As Variant
    Dim coords2(2) As Variant

    Call mAxisSystem.GetZort(tmpData)
    mtrxData(0, 0) = tmpData(0)
    mtrxData(0, 1) = tmpData(1)
    mtrxData(0, 2) = tmpData(2)

    Call mAxisSystem.GetXort(tmpData)
    mtrxData(1, 0) = tmpData(0)
    mtrxData(1, 1) = tmpData(1)
    mtrxData(1, 2) = tmpData(2)

    Set pointToGetCoords = midPoints(6)
    pointToGetCoords.GetCoordinates coords1
    Set pointToGetCoords = midPoints(7)
    pointToGetCoords.GetCoordinates coords2

    Call mAxisSystem.GetXort(tmpData)
    mtrxData(2, 0) = coords1(0) - coords2(0)
    mtrxData(2, 1) = coords1(1) - coords2(1)
    mtrxData(2, 2) = coords1(2) - coords2(2)

    Dim MatrixZX As New Matrix
    MatrixZX.SetDimension 3
    MatrixZX.SetData mtrxData

    Call mAxisSystem.GetYort(tmpData)
    mtrxData(1, 0) = tmpData(0)
    mtrxData(1, 1) = tmpData(1)
    mtrxData(1, 2) = tmpData(2)

    Dim MatrixZY As New Matrix
    MatrixZY.SetDimension 3
    MatrixZY.SetData mtrxData

' Det of       Det of       Quarter of
' MatrixZX     MatrixZY     Theta angle
'    +            -             I
'    -            -             IV
'    +            +             II
'    -            +             III

    If (pTheta > 0# And pTheta <= 90#) Then
        If (MatrixZX.Det > 0#) Then
            If (MatrixZY.Det < 0#) Then
                ' I
                ' OK
            Else
                ' II
                pTheta = 180# - pTheta
            End If
        Else
            If (MatrixZY.Det < 0#) Then
                ' IV
                pTheta = -pTheta
            Else
                ' III
                pTheta = pTheta - 180#
            End If
        End If
    ElseIf (pTheta > 90# And pTheta <= 180#) Then
        If (MatrixZX.Det > 0#) Then
            If (MatrixZY.Det < 0#) Then
                ' I
                pTheta = 180# - pTheta
            Else
                ' II
                ' OK
            End If
        Else
            If (MatrixZY.Det < 0#) Then
                ' IV
                pTheta = pTheta - 180#
            Else
                ' III
                pTheta = -pTheta
            End If
        End If
    ElseIf (pTheta = 0#) Then
        pTheta = 0#
    'ElseIf (pPhi = 180#) Then
        'TODO - maybe implement ?s
    Else
        MsgBox "Warning. Strange Phi computed.", vbExclamation
    End If

End Sub

Attribute VB_Name = "mySphere"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' mySphere class

Option Explicit

Const TOLERANCE = 10

' -- Data members ----------------------------------------------------------------------

Dim pickedPoints(1 To 8) As HybridShapePointCoord

' pointer to singleton myFactory object
Dim myFac As myFactory

' temporary construct element
Dim checkPlanes(1 To 2) As HybridShapePlane3Points
Dim lines(1 To 4) As HybridShapeLinePtPt
Dim centers(1 To 2) As HybridShapeIntersection
Dim planes(1 To 4) As HybridShapePlane2Lines

Dim Zaxis As HybridShapeIntersection
Dim Yaxis As HybridShapeIntersection
Dim Xaxis As HybridShapeLineNormal
Dim YZplane As HybridShapePlane2Lines
Dim s As HybridShapeSphere
Dim Zorts As HybridShapeIntersection
Dim Xorts As HybridShapeIntersection
Dim Yorts As HybridShapeIntersection
Dim Zort As HybridShape
Dim Xort As HybridShape
Dim Yort As HybridShape
Dim Zort2 As HybridShape
Dim Xort2 As HybridShape
Dim Yort2 As HybridShape

' recognized parameters
Dim pRmin As Double
Dim pRmax As Double
Dim pSPhi As Double
Dim pDPhi As Double
Dim pSTheta As Double
Dim pDTheta As Double

' recognized axis system
Dim mAxisSystem As New myAxisSystem

' -- Methods ---------------------------------------------------------------------------

Public Sub SetFactory(ByRef p_fac As myFactory)

    Set myFac = p_fac

End Sub

Public Sub SetPickedPoints(p1 As HybridShapePointCoord, p2 As HybridShapePointCoord, _
                            p3 As HybridShapePointCoord, p4 As HybridShapePointCoord, _
                            p5 As HybridShapePointCoord, p6 As HybridShapePointCoord, _
                            p7 As HybridShapePointCoord, p8 As HybridShapePointCoord)

    Set pickedPoints(1) = p1
    Set pickedPoints(2) = p2
    Set pickedPoints(3) = p3
    Set pickedPoints(4) = p4
    Set pickedPoints(5) = p5
    Set pickedPoints(6) = p6
    Set pickedPoints(7) = p7
    Set pickedPoints(8) = p8

End Sub

Public Sub SetPickedPoints2(pts() As HybridShapePointCoord)

    Me.SetPickedPoints pts(1), pts(2), pts(3), pts(4), pts(5), pts(6), pts(7), pts(8)

End Sub

Public Sub BuildConstructPre()

    myFac.BuildLine pickedPoints(3), pickedPoints(2), lines(1), "line.CB"
    myFac.BuildLine pickedPoints(4), pickedPoints(1), lines(2), "line.DA"
    myFac.BuildLine pickedPoints(7), pickedPoints(6), lines(3), "line.GF"
    myFac.BuildLine pickedPoints(8), pickedPoints(5), lines(4), "line.HE"

    ' Update
    myFac.myUpdate

End Sub

Public Sub FixPointsOrder()

    Dim tmpPoint As HybridShapePointCoord

    If ((Round(myFac.GetAngle(lines(1), lines(2)), TOLERANCE) = 0 Or _
            Round(myFac.GetAngle(lines(1), lines(2)), TOLERANCE) = 180) And _
            (Round(myFac.GetAngle(lines(3), lines(4)), TOLERANCE) = 0 Or _
            Round(myFac.GetAngle(lines(3), lines(4)), TOLERANCE) = 180)) Then

        ' Remove wrong lines
        myFac.RemovePreConstruct lines(1)
        myFac.RemovePreConstruct lines(2)
        myFac.RemovePreConstruct lines(3)
        myFac.RemovePreConstruct lines(4)

        ' Shift points circular
        Set tmpPoint = pickedPoints(1)
        Set pickedPoints(1) = pickedPoints(2)
        Set pickedPoints(2) = pickedPoints(3)
        Set pickedPoints(3) = pickedPoints(4)
        Set pickedPoints(4) = tmpPoint
        Set tmpPoint = pickedPoints(5)
        Set pickedPoints(5) = pickedPoints(6)
        Set pickedPoints(6) = pickedPoints(7)
        Set pickedPoints(7) = pickedPoints(8)
        Set pickedPoints(8) = tmpPoint

        ' Construct new lines and planes
        BuildConstructPre

    Else

    End If

    If (myFac.GetDistance(pickedPoints(1), pickedPoints(2)) > myFac.GetDistance(pickedPoints(3), pickedPoints(4))) Then

        ' Remove wrong lines
        myFac.RemovePreConstruct lines(1)
        myFac.RemovePreConstruct lines(2)
        myFac.RemovePreConstruct lines(3)
        myFac.RemovePreConstruct lines(4)

        ' Swap outer point and inner points
        Set tmpPoint = pickedPoints(1)
        Set pickedPoints(1) = pickedPoints(4)
        Set pickedPoints(4) = tmpPoint
        Set tmpPoint = pickedPoints(2)
        Set pickedPoints(2) = pickedPoints(3)
        Set pickedPoints(3) = tmpPoint
        Set tmpPoint = pickedPoints(5)
        Set pickedPoints(5) = pickedPoints(8)
        Set pickedPoints(8) = tmpPoint
        Set tmpPoint = pickedPoints(7)
        Set pickedPoints(7) = pickedPoints(6)
        Set pickedPoints(6) = tmpPoint

        ' Construct new lines and planes
        BuildConstructPre

    Else

    End If

End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8

    ' Update
    myFac.myUpdate

    ' Check planarity of the selected groups of points
    formPrimitiveCreator.TextBox2.Text = myFac.GetDistance(checkPlanes(1), pickedPoints(4))
    formPrimitiveCreator.TextBox3.Text = myFac.GetDistance(checkPlanes(2), pickedPoints(8))

    ' Build the center of the primitive in two different ways
    myFac.BuildIntersectionPoint lines(1), lines(2), centers(1), "center.1"
    myFac.BuildIntersectionPoint lines(3), lines(4), centers(2), "center.2"

    ' Build bounding planes
    myFac.BuildPlane lines(1), lines(2), planes(1), "plane.1.theta"
    myFac.BuildPlane lines(3), lines(4), planes(2), "plane.2.theta"
    myFac.BuildPlane lines(1), lines(3), planes(3), "plane.1.phi"
    myFac.BuildPlane lines(2), lines(4), planes(4), "plane.2.phi"

    ' Build axes of the primitive
    myFac.BuildIntersectionLine planes(1), planes(2), Yaxis, "YaxisOfThePrimitive"
    myFac.BuildIntersectionLine planes(3), planes(4), Zaxis, "ZaxisOfThePrimitive"

    ' Build YZ plane of the primitive
    myFac.BuildPlane Zaxis, Yaxis, YZplane, "plane.YZ"
    myFac.BuildNormalToPlane YZplane, centers(1), Xaxis, "XaxisOfThePrimitive"

    ' Update
    myFac.myUpdate

    ' Check that the center of the primitive found two different ways is the same within tolerance
    formPrimitiveCreator.TextBox1.Text = myFac.GetDistance(centers(1), centers(2))

    ' Build a sphere, its intersection with the Z axis and 'near' to define the positive direction of the Z axis
    myFac.BuildSphere centers(1), 1#, s, "sphere.identity"
    myFac.BuildIntersection s, Zaxis, Zorts, "Zorts"
    myFac.BuildIntersection s, Xaxis, Xorts, "Xorts"
    myFac.BuildIntersection s, Yaxis, Yorts, "Yorts"
    myFac.SelectNearestPoint Zorts, lines(1), Zort, "Zort"
    myFac.SelectNearestPoint Xorts, lines(1), Xort, "Xort"
    myFac.SelectNearestPoint Yorts, lines(1), Yort, "Yort"
    myFac.BuildPoint Zort, Zort2, "Zort2"
    myFac.BuildPoint Xort, Xort2, "Xort2"
    myFac.BuildPoint Yort, Yort2, "Yort2"

    ' Update
    myFac.myUpdate
    
    ' Compute coordinate system
    Dim v_pointToExtractCoordinates
    Dim v_tmpVariant(2)
    Dim v_tmpDouble(2) As Double
    Dim v_tmpCenter(2) As Double
    Dim centaxis As HybridShape
    Dim cent
    
    myFac.Center centers(2), v_tmpCenter
    mAxisSystem.SetCenter v_tmpCenter    ' Set center of the axis system

'    Set v_pointToExtractCoordinates = Zort2
'    v_pointToExtractCoordinates.GetCoordinates v_tmpVariant
'    v_tmpDouble(0) = v_tmpVariant(0) - v_tmpCenter(0)
'    v_tmpDouble(1) = v_tmpVariant(1) - v_tmpCenter(1)
'    v_tmpDouble(2) = v_tmpVariant(2) - v_tmpCenter(2)
'    mAxisSystem.SetZort v_tmpDouble      ' Set Z direction of the axis system

    Set v_pointToExtractCoordinates = Yort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetYort v_tmpDouble      ' Set X direction of the axis system
    
    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Y direction of the axis system
    

  '  mAxisSystem.ComputeYort              ' Compute the last Y direction from given Z and X directions
     mAxisSystem.ComputeXort
  '  mAxisSystem.ComputeZort

End Sub

Public Sub Recognize()

    ' Compute pRmin
    Dim minRs(1 To 4) As Double     ' TODO check which one to choose. They must be all equal.
    minRs(1) = myFac.GetDistance(centers(1), pickedPoints(1))
    minRs(2) = myFac.GetDistance(centers(1), pickedPoints(2))
    minRs(3) = myFac.GetDistance(centers(1), pickedPoints(5))
    minRs(4) = myFac.GetDistance(centers(1), pickedPoints(6))
    pRmin = Round(minRs(1), TOLERANCE)
    formPrimitiveCreator.ListBox1.AddItem "pRmin = " & pRmin

    ' Compute pRmax
    Dim maxRs(1 To 4) As Double     ' TODO check which one to choose. They must be all equal.
    maxRs(1) = myFac.GetDistance(centers(1), pickedPoints(3))
    maxRs(2) = myFac.GetDistance(centers(1), pickedPoints(4))
    maxRs(3) = myFac.GetDistance(centers(1), pickedPoints(7))
    maxRs(4) = myFac.GetDistance(centers(1), pickedPoints(8))
    pRmax = Round(maxRs(1), TOLERANCE)
    formPrimitiveCreator.ListBox1.AddItem "pRmax = " & pRmax


    ' Compute pDPhi theta -> phi !!!
    'Dim DPhi As Double
        
    DPhi = myFac.GetAngle(planes(3), planes(4))
    pDPhi = Round(DPhi, TOLERANCE)

    ' Compute pSPhi 'Angle Between Plane ZX and Plane1(2).Phi
    Dim SPhi As Double
    'Dim PlaneZX As Object
    'myFac.GetStandartPlaneZX PlaneZX
    'Dim pl As HybridShape
    'Set pl = PlaneZX
    'SPhi = myFac.GetAngle(planes(3), pl)
    'can not be determined unambiguously
    SPhi = DPhi / 2#
    pSPhi = Round(SPhi, TOLERANCE)

    ' Compute pSTheta
    Dim SThetas(1 To 2) As Double   ' TODO check which one to choose. They must be all equal. Zaxis -> Yaxis
    SThetas(1) = myFac.GetAngle(lines(1), Zaxis)
    SThetas(2) = myFac.GetAngle(lines(3), Zaxis)
    Dim i As Integer
    For i = 1 To 2
        If (SThetas(i) > 90#) Then SThetas(i) = 180# - SThetas(i)
    Next i
    pSTheta = Round(SThetas(1), TOLERANCE)
    
    ' Compute pDTheta phi -> theta !!!
  
    Dim DThetas(1 To 2) As Double   ' TODO check which one to choose. They must be all equal.
    DThetas(1) = myFac.GetAngle(lines(1), lines(3))
    DThetas(2) = myFac.GetAngle(lines(2), lines(4))
    MsgBox ("theta1=" & DThetas(1) & "theta2=" & DThetas(2))
    pDTheta = Round(DThetas(1), TOLERANCE)
    
    formPrimitiveCreator.ListBox1.AddItem "pSPhi = " & pSPhi
    formPrimitiveCreator.ListBox1.AddItem "pDPhi = " & pDPhi
    formPrimitiveCreator.ListBox1.AddItem "pSTheta = " & pSTheta
    formPrimitiveCreator.ListBox1.AddItem "pDTheta = " & pDTheta

End Sub
Public Sub GetAxisSystem(ByRef o_axSystem As myAxisSystem)
    Set o_axSystem = mAxisSystem
End Sub
Public Sub ApplyParametersToUDF(shpInst As ShapeInstance)

    Call shpInst.GetParameter("pRmin").ValuateFromString(Trim(Str(pRmin)) + "mm")
    Call shpInst.GetParameter("pRmax").ValuateFromString(Trim(Str(pRmax)) + "mm")
    Call shpInst.GetParameter("pDPhi").ValuateFromString(Trim(Str(pDPhi)) + "deg")
    Call shpInst.GetParameter("pSPhi").ValuateFromString(Trim(Str(pSPhi)) + "deg")
    Call shpInst.GetParameter("pDTheta").ValuateFromString(Trim(Str(pDTheta)) + "deg")
    Call shpInst.GetParameter("pSTheta").ValuateFromString(Trim(Str(pSTheta)) + "deg")

End Sub

Attribute VB_Name = "myTrap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myTrap class

Option Explicit

Const TOLERANCE = 10

' -- Data members ----------------------------------------------------------------------

Dim pickedPoints(1 To 8) As HybridShapePointCoord

' pointer to singleton myFactory object
Dim myFac As myFactory

' temporary construct element
Dim checkPlanes(1 To 4) As HybridShapePlane3Points
Dim lines(1 To 7) As HybridShapeLinePtPt
Dim midPoints(1 To 7) As HybridShapePointBetween
Dim planes(1 To 2) As HybridShapePlane2Lines ' bottom and top planes
Dim Yaces(1 To 2) As HybridShapeLineAngle
Dim Xaxis As HybridShapeLineAngle
Dim Zaxis As HybridShapeLineNormal
Dim orientPlane As HybridShapePlane2Lines ' for phi measurement
Dim ZXplane As HybridShapePlane2Lines     ' for phi measurement

' for AxisSystem
Dim Zaxis2 As HybridShapeLineNormal
Dim Xort As HybridShape
Dim s As HybridShapeSphere
Dim Zorts As HybridShapeIntersection
Dim Zort As HybridShape
Dim Zort2 As HybridShape

' recognized parameters
Dim pDz As Double
Dim pTheta As Double
Dim pPhi As Double
Dim pDy1 As Double
Dim pDx1 As Double
Dim pDx2 As Double
Dim pAlpha As Double
Dim pDy2 As Double
Dim pDx3 As Double
Dim pDx4 As Double

' recognized axis system
Dim mAxisSystem As New myAxisSystem

' -- Methods ---------------------------------------------------------------------------

Public Sub SetFactory(ByRef p_fac As myFactory)

    Set myFac = p_fac

End Sub

Public Sub SetPickedPoints(p_p1 As HybridShapePointCoord, p_p2 As HybridShapePointCoord, _
                            p_p3 As HybridShapePointCoord, p_p4 As HybridShapePointCoord, _
                            p_p5 As HybridShapePointCoord, p_p6 As HybridShapePointCoord, _
                            p_p7 As HybridShapePointCoord, p_p8 As HybridShapePointCoord)

    Set pickedPoints(1) = p_p1
    Set pickedPoints(2) = p_p2
    Set pickedPoints(3) = p_p3
    Set pickedPoints(4) = p_p4
    Set pickedPoints(5) = p_p5
    Set pickedPoints(6) = p_p6
    Set pickedPoints(7) = p_p7
    Set pickedPoints(8) = p_p8

End Sub

Public Sub SetPickedPoints2(p_pts() As HybridShapePointCoord)

    Me.SetPickedPoints p_pts(1), p_pts(2), p_pts(3), p_pts(4), p_pts(5), p_pts(6), p_pts(7), p_pts(8)

End Sub

Public Sub BuildConstructPre()

    myFac.BuildLine pickedPoints(1), pickedPoints(4), lines(1), "line.AD"
    myFac.BuildLine pickedPoints(2), pickedPoints(3), lines(2), "line.BC"
    myFac.BuildLine pickedPoints(5), pickedPoints(8), lines(3), "line.EH"
    myFac.BuildLine pickedPoints(6), pickedPoints(7), lines(4), "line.FG"

    ' Update
    myFac.myUpdate

End Sub

Public Sub FixPointsOrder()

    Dim tmpPoint As HybridShapePointCoord

    Dim coords1(2) As Variant
    Dim coords2(2) As Variant
    Dim mtrxData(2, 2) As Double

    Dim pointToGetCoords

    Set pointToGetCoords = pickedPoints(1)
    pointToGetCoords.GetCoordinates coords1

    Set pointToGetCoords = pickedPoints(4)
    pointToGetCoords.GetCoordinates coords2
    mtrxData(0, 0) = coords2(0) - coords1(0)        ' x    of vector 14
    mtrxData(0, 1) = coords2(1) - coords1(1)        ' y    of vector 14
    mtrxData(0, 2) = coords2(2) - coords1(2)        ' z    of vector 14

    Set pointToGetCoords = pickedPoints(2)
    pointToGetCoords.GetCoordinates coords2
    mtrxData(1, 0) = coords2(0) - coords1(0)        ' x    of vector 12
    mtrxData(1, 1) = coords2(1) - coords1(1)        ' y    of vector 12
    mtrxData(1, 2) = coords2(2) - coords1(2)        ' z    of vector 12

    Set pointToGetCoords = pickedPoints(5)
    pointToGetCoords.GetCoordinates coords2
    mtrxData(2, 0) = coords2(0) - coords1(0)        ' x    of vector 15
    mtrxData(2, 1) = coords2(1) - coords1(1)        ' y    of vector 15
    mtrxData(2, 2) = coords2(2) - coords1(2)        ' z    of vector 15

    Dim tmpM As New Matrix
    tmpM.SetDimension 3
    tmpM.SetData mtrxData

    'MsgBox tmpM.Det

    If (tmpM.Det < 0) Then

        ' Remove wrong lines and planes
        myFac.RemovePreConstruct lines(1)
        myFac.RemovePreConstruct lines(2)
        myFac.RemovePreConstruct lines(3)
        myFac.RemovePreConstruct lines(4)

        ' exchange 2 <-> 4 and 6 <-> 8
        MsgBox "Swap2"
        Set tmpPoint = pickedPoints(2)
        Set pickedPoints(2) = pickedPoints(4)
        Set pickedPoints(4) = tmpPoint
        Set tmpPoint = pickedPoints(6)
        Set pickedPoints(6) = pickedPoints(8)
        Set pickedPoints(8) = tmpPoint

        ' Construct new lines and planes
        BuildConstructPre

    End If

    'MsgBox Str(myFac.GetAngle(lines(1), lines(2))) & vbNewLine & Str(myFac.GetAngle(lines(3), lines(4)))

    If Not ((Round(myFac.GetAngle(lines(1), lines(2)), TOLERANCE) = 0 Or _
            Round(myFac.GetAngle(lines(1), lines(2)), TOLERANCE) = 180) And _
            (Round(myFac.GetAngle(lines(3), lines(4)), TOLERANCE) = 0 Or _
            Round(myFac.GetAngle(lines(3), lines(4)), TOLERANCE) = 180)) Then

        ' Remove wrong lines and planes
        myFac.RemovePreConstruct lines(1)
        myFac.RemovePreConstruct lines(2)
        myFac.RemovePreConstruct lines(3)
        myFac.RemovePreConstruct lines(4)

        ' Swap points
        MsgBox "Swap"
        Set tmpPoint = pickedPoints(1)
        Set pickedPoints(1) = pickedPoints(2)
        Set pickedPoints(2) = pickedPoints(3)
        Set pickedPoints(3) = pickedPoints(4)
        Set pickedPoints(4) = tmpPoint
        Set tmpPoint = pickedPoints(5)
        Set pickedPoints(5) = pickedPoints(6)
        Set pickedPoints(6) = pickedPoints(7)
        Set pickedPoints(7) = pickedPoints(8)
        Set pickedPoints(8) = tmpPoint

        ' Construct new lines and planes
        BuildConstructPre

    End If

End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8
    myFac.BuildPlane3Pt pickedPoints(2), pickedPoints(3), pickedPoints(6), checkPlanes(3), "plane.3.check" '7
    myFac.BuildPlane3Pt pickedPoints(1), pickedPoints(4), pickedPoints(5), checkPlanes(4), "plane.4.check" '8

    ' Update
    myFac.myUpdate

    ' Check planarity of some faces
    formPrimitiveCreator.TextBox2.Text = myFac.GetDistance(checkPlanes(1), pickedPoints(4))
    formPrimitiveCreator.TextBox3.Text = myFac.GetDistance(checkPlanes(2), pickedPoints(8))
    formPrimitiveCreator.TextBox4.Text = myFac.GetDistance(checkPlanes(3), pickedPoints(7))
    formPrimitiveCreator.TextBox5.Text = myFac.GetDistance(checkPlanes(4), pickedPoints(8))

    ' Build all the middle points and lines, connecting them
    myFac.BuildMidPoint2 pickedPoints(1), pickedPoints(4), midPoints(1), "point.mid.1"
    myFac.BuildMidPoint2 pickedPoints(2), pickedPoints(3), midPoints(2), "point.mid.2"
    myFac.BuildMidPoint2 pickedPoints(5), pickedPoints(8), midPoints(3), "point.mid.3"
    myFac.BuildMidPoint2 pickedPoints(6), pickedPoints(7), midPoints(4), "point.mid.4"
    myFac.BuildLine midPoints(1), midPoints(2), lines(5), "line.bottom.mid"
    myFac.BuildLine midPoints(3), midPoints(4), lines(6), "line.top.mid"
    myFac.BuildMidPoint2 midPoints(1), midPoints(2), midPoints(5), "point.mid.5"
    myFac.BuildMidPoint2 midPoints(3), midPoints(4), midPoints(6), "point.mid.6"
    myFac.BuildLine midPoints(5), midPoints(6), lines(7), "line.mid"
    myFac.BuildMidPoint2 midPoints(5), midPoints(6), midPoints(7), "point.center"

    ' Build top and botton planes
    myFac.BuildPlane lines(1), lines(2), planes(1), "plane.bottom"
    myFac.BuildPlane lines(3), lines(4), planes(2), "plane.top"

    ' Build Y axis in both planes
    myFac.BuildNormalToLine lines(1), planes(1), midPoints(1), Yaces(1), "line.bottom.Y"
    myFac.BuildNormalToLine lines(3), planes(2), midPoints(3), Yaces(2), "line.top.Y"

    ' Build X axis of the primitive
    myFac.BuildParallelLine lines(1), planes(1), midPoints(7), Xaxis, "XaxisOfThePrimitive"

    ' Build Z axis of the primitive - needed to measure phi
    myFac.BuildNormalToPlane planes(1), midPoints(7), Zaxis, "ZaxisOfThePrimitive"

    ' Update
    myFac.myUpdate

    ' if Z axis of the primitive does not coincide with the middle line of the primitive
    If (Round(myFac.GetAngle(lines(7), Zaxis), TOLERANCE) <> 0 And _
        Round(myFac.GetAngle(lines(7), Zaxis), TOLERANCE) <> 180) Then

        ' Build the plane through the Z axis and the middle line of the primitive
        myFac.BuildPlane lines(7), Zaxis, orientPlane, "plane.orientation"
    
        ' Build ZX plane of the primitive
        myFac.BuildPlane Zaxis, Xaxis, ZXplane, "plane.ZX"

    End If

' 10jan2015

    ' Build line parallel to Z axis going from the midpoint1 - needed for AxisSystem building
    myFac.BuildNormalToPlane planes(1), midPoints(1), Zaxis2, "Zaxis2"

    ' Build the point which will define the X ort the AxisSystem of the primitive
    myFac.BuildPoint2 lines(1), midPoints(1), Xort, "Xort"
    
    myFac.BuildSphere midPoints(1), 1#, s, "sphere.identity"
    myFac.BuildIntersection s, Zaxis2, Zorts, "Zorts"
    myFac.SelectNearestPoint Zorts, planes(2), Zort, "Zort"
    myFac.BuildPoint Zort, Zort2, "Zort2"


    ' Update
    myFac.myUpdate

    ' Extract axis system of the primitve

    Dim v_pointToExtractCoordinates
    Dim v_tmpVariant(2)
    Dim v_tmpDouble(2) As Double
    Dim v_tmpCenter(2) As Double
    Dim v_tmpLocCenter(2) As Double

    Set v_pointToExtractCoordinates = midPoints(7)
    v_pointToExtractCoordinates.GetCoordinates v_tmpVariant
    v_tmpCenter(0) = v_tmpVariant(0)
    v_tmpCenter(1) = v_tmpVariant(1)
    v_tmpCenter(2) = v_tmpVariant(2)
    mAxisSystem.SetCenter v_tmpCenter    ' Set center of the axis system

    Set v_pointToExtractCoordinates = midPoints(1)
    v_pointToExtractCoordinates.GetCoordinates v_tmpVariant
    v_tmpLocCenter(0) = v_tmpVariant(0)
    v_tmpLocCenter(1) = v_tmpVariant(1)
    v_tmpLocCenter(2) = v_tmpVariant(2)

    Set v_pointToExtractCoordinates = Zort2
    v_pointToExtractCoordinates.GetCoordinates v_tmpVariant
    v_tmpDouble(0) = v_tmpVariant(0) - v_tmpLocCenter(0)
    v_tmpDouble(1) = v_tmpVariant(1) - v_tmpLocCenter(1)
    v_tmpDouble(2) = v_tmpVariant(2) - v_tmpLocCenter(2)
    mAxisSystem.SetZort v_tmpDouble      ' Set Z direction of the axis system

    Set v_pointToExtractCoordinates = Xort
    v_pointToExtractCoordinates.GetCoordinates v_tmpVariant
    v_tmpDouble(0) = v_tmpVariant(0) - v_tmpLocCenter(0)
    v_tmpDouble(1) = v_tmpVariant(1) - v_tmpLocCenter(1)
    v_tmpDouble(2) = v_tmpVariant(2) - v_tmpLocCenter(2)
    mAxisSystem.SetXort v_tmpDouble      ' Set X direction of the axis system

    mAxisSystem.ComputeYort              ' Compute the last Y direction from given Z and X directions

    'Call mAxisSystem.Draw

End Sub

Public Sub Recognize()

    ' Extract parameters of the primitive

    pDz = Round(myFac.GetDistance(planes(1), planes(2)) / 2#, TOLERANCE)

    ' if Z axis of the primitive does not coincide with the middle line of the primitive
    If (Round(myFac.GetAngle(lines(7), Zaxis), TOLERANCE) <> 0 And _
        Round(myFac.GetAngle(lines(7), Zaxis), TOLERANCE) <> 180) Then
        pTheta = Round(myFac.GetAngle(Zaxis, lines(7)), TOLERANCE)
        pPhi = Round(myFac.GetAngle(orientPlane, ZXplane), TOLERANCE)
        Call ImproveTheta
        Call ImprovePhi
    Else
        pTheta = 0
        pPhi = 0
    End If

    pDy1 = Round(myFac.GetDistance(lines(1), lines(2)) / 2#, TOLERANCE)
    pDx1 = Round(myFac.GetDistance(pickedPoints(1), pickedPoints(4)) / 2#, TOLERANCE)
    pDx2 = Round(myFac.GetDistance(pickedPoints(2), pickedPoints(3)) / 2#, TOLERANCE)
    pAlpha = Round(myFac.GetAngle(Yaces(1), lines(5)), TOLERANCE) ' or   myFac.GetAngle(Yaces(2), lines(6))   ' TODO check which one to choose. They must be all equal.

    Call ImproveAlpha

    pDy2 = Round(myFac.GetDistance(lines(3), lines(4)) / 2#, TOLERANCE)
    pDx3 = Round(myFac.GetDistance(pickedPoints(5), pickedPoints(8)) / 2#, TOLERANCE)
    pDx4 = Round(myFac.GetDistance(pickedPoints(6), pickedPoints(7)) / 2#, TOLERANCE)

    formPrimitiveCreator.ListBox1.AddItem "pDz = " & Trim(Str(pDz))
    formPrimitiveCreator.ListBox1.AddItem "pTheta = " & Trim(Str(pTheta))
    formPrimitiveCreator.ListBox1.AddItem "pPhi = " & Trim(Str(pPhi))
    formPrimitiveCreator.ListBox1.AddItem "pDy1 = " & Trim(Str(pDy1))
    formPrimitiveCreator.ListBox1.AddItem "pDx1 = " & Trim(Str(pDx1))
    formPrimitiveCreator.ListBox1.AddItem "pDx2 = " & Trim(Str(pDx2))
    formPrimitiveCreator.ListBox1.AddItem "pAlpha1 = " & Trim(Str(pAlpha))
    'formPrimitiveCreator.ListBox1.AddItem "pAlpha2 = " & Trim(Str(myFac.GetAngle(Yaces(2), lines(6))))
    formPrimitiveCreator.ListBox1.AddItem "pDy2 = " & Trim(Str(pDy2))
    formPrimitiveCreator.ListBox1.AddItem "pDx3 = " & Trim(Str(pDx3))
    formPrimitiveCreator.ListBox1.AddItem "pDx4 = " & Trim(Str(pDx4))

End Sub

Public Sub ApplyParametersToUDF(shpInst As ShapeInstance)

    Call shpInst.GetParameter("pDz").ValuateFromString(Trim(Str(pDz)) + "mm")
    Call shpInst.GetParameter("pTheta").ValuateFromString(Trim(Str(pTheta)) + "deg")
    Call shpInst.GetParameter("pPhi").ValuateFromString(Trim(Str(pPhi)) + "deg")
    Call shpInst.GetParameter("pDy1").ValuateFromString(Trim(Str(pDy1)) + "mm")
    Call shpInst.GetParameter("pDx1").ValuateFromString(Trim(Str(pDx1)) + "mm")
    Call shpInst.GetParameter("pDx2").ValuateFromString(Trim(Str(pDx2)) + "mm")
    Call shpInst.GetParameter("pAlp1").ValuateFromString(Trim(Str(pAlpha)) + "deg")
    Call shpInst.GetParameter("pDy2").ValuateFromString(Trim(Str(pDy2)) + "mm")
    Call shpInst.GetParameter("pDx3").ValuateFromString(Trim(Str(pDx3)) + "mm")
    Call shpInst.GetParameter("pDx4").ValuateFromString(Trim(Str(pDx4)) + "mm")

End Sub

Public Sub GetAxisSystem(ByRef o_axSystem As myAxisSystem)
    Set o_axSystem = mAxisSystem
End Sub

Public Sub ImproveAlpha()

    If (pAlpha >= 90#) Then
        'MsgBox "Measured alpha >= 90"
        pAlpha = 180# - pAlpha
    End If

    If (pAlpha <> 0) Then
        If (myFac.GetDistance(pickedPoints(1), midPoints(2)) < myFac.GetDistance(pickedPoints(4), midPoints(2))) Then
            pAlpha = -pAlpha
        End If
    End If

End Sub

Public Sub ImproveTheta()

    If (pTheta > 90# And pTheta <= 180#) Then
        pTheta = 180# - pTheta
    ElseIf (pTheta > 180#) Then
        MsgBox "Measured Theta > 180deg"
    ElseIf (pTheta >= 0# And pTheta <= 90#) Then
        ' OK
    End If

End Sub

Public Sub ImprovePhi()

    Dim mtrxData(2, 2) As Double
    Dim tmpData(2) As Double

    Dim pointToGetCoords
    Dim coords1(2) As Variant
    Dim coords2(2) As Variant

    Call mAxisSystem.GetZort(tmpData)
    mtrxData(0, 0) = tmpData(0)
    mtrxData(0, 1) = tmpData(1)
    mtrxData(0, 2) = tmpData(2)

    Call mAxisSystem.GetXort(tmpData)
    mtrxData(1, 0) = tmpData(0)
    mtrxData(1, 1) = tmpData(1)
    mtrxData(1, 2) = tmpData(2)

    Set pointToGetCoords = midPoints(6)
    pointToGetCoords.GetCoordinates coords1
    Set pointToGetCoords = midPoints(7)
    pointToGetCoords.GetCoordinates coords2

    Call mAxisSystem.GetXort(tmpData)
    mtrxData(2, 0) = coords1(0) - coords2(0)
    mtrxData(2, 1) = coords1(1) - coords2(1)
    mtrxData(2, 2) = coords1(2) - coords2(2)

    Dim MatrixZX As New Matrix
    MatrixZX.SetDimension 3
    MatrixZX.SetData mtrxData

    Call mAxisSystem.GetYort(tmpData)
    mtrxData(1, 0) = tmpData(0)
    mtrxData(1, 1) = tmpData(1)
    mtrxData(1, 2) = tmpData(2)

    Dim MatrixZY As New Matrix
    MatrixZY.SetDimension 3
    MatrixZY.SetData mtrxData

' Det of       Det of       Quarter of
' MatrixZX     MatrixZY     Phi angle
'    +            -             I
'    -            -             IV
'    +            +             II
'    -            +             III

    If (pPhi > 0# And pPhi <= 90#) Then
        If (MatrixZX.Det > 0#) Then
            If (MatrixZY.Det < 0#) Then
                ' I
                ' OK
            Else
                ' II
                pPhi = 180# - pPhi
            End If
        Else
            If (MatrixZY.Det < 0#) Then
                ' IV
                pPhi = -pPhi
            Else
                ' III
                pPhi = pPhi - 180#
            End If
        End If
    ElseIf (pPhi > 90# And pPhi <= 180#) Then
        If (MatrixZX.Det > 0#) Then
            If (MatrixZY.Det < 0#) Then
                ' I
                pPhi = 180# - pPhi
            Else
                ' II
                ' OK
            End If
        Else
            If (MatrixZY.Det < 0#) Then
                ' IV
                pPhi = pPhi - 180#
            Else
                ' III
                pPhi = -pPhi
            End If
        End If
    ElseIf (pPhi = 0# Or pPhi = 180#) Then
        If (MatrixZY.Det > 0#) Then
            pPhi = 180#
        Else
            pPhi = 0#
        End If
    Else
        MsgBox "Warning. Strange Phi computed.", vbExclamation
    End If

End Sub

Attribute VB_Name = "myTrd"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myTrd class

Option Explicit

Const TOLERANCE = 10

' -- Data members ----------------------------------------------------------------------

Dim pickedPoints(1 To 8) As HybridShapePointCoord

' pointer to singleton myFactory object
Dim myFac As myFactory

' temporary construct element
Dim lines(1 To 7) As HybridShapeLinePtPt
Dim midPoints(1 To 7) As HybridShapePointBetween
Dim planes(1 To 2) As HybridShapePlane2Lines
Dim checkPlanes(1 To 4) As HybridShapePlane3Points
Dim Zaxis As HybridShapeLineNormal
Dim Xaxis As HybridShapeLineAngle
Dim Yaces(1 To 2) As HybridShapeLineAngle
Dim orientPlane As HybridShapePlane2Lines
Dim ZXplane As HybridShapePlane2Lines
Dim s As HybridShapeSphere
Dim Zorts As HybridShapeIntersection
Dim Xorts As HybridShapeIntersection
Dim Zort As HybridShape
Dim Xort As HybridShape
Dim Zort2 As HybridShape
Dim Xort2 As HybridShape

' recognized parameters
Dim pDx1 As Double
Dim pDy1 As Double
Dim pDx2 As Double
Dim pDy2 As Double
Dim pDz As Double

' recognized axis system
Dim mAxisSystem As New myAxisSystem

' -- Methods ---------------------------------------------------------------------------

Public Sub SetFactory(ByRef p_fac As myFactory)

    Set myFac = p_fac

End Sub

Public Sub SetPickedPoints(p_p1 As HybridShapePointCoord, p_p2 As HybridShapePointCoord, _
                            p_p3 As HybridShapePointCoord, p_p4 As HybridShapePointCoord, _
                            p_p5 As HybridShapePointCoord, p_p6 As HybridShapePointCoord, _
                            p_p7 As HybridShapePointCoord, p_p8 As HybridShapePointCoord)

    Set pickedPoints(1) = p_p1
    Set pickedPoints(2) = p_p2
    Set pickedPoints(3) = p_p3
    Set pickedPoints(4) = p_p4
    Set pickedPoints(5) = p_p5
    Set pickedPoints(6) = p_p6
    Set pickedPoints(7) = p_p7
    Set pickedPoints(8) = p_p8

End Sub

Public Sub SetPickedPoints2(p_pts() As HybridShapePointCoord)

    Me.SetPickedPoints p_pts(1), p_pts(2), p_pts(3), p_pts(4), p_pts(5), p_pts(6), p_pts(7), p_pts(8)

End Sub

Public Sub BuildConstructPre()

    myFac.BuildLine pickedPoints(1), pickedPoints(4), lines(1), "line.AD"
    myFac.BuildLine pickedPoints(2), pickedPoints(3), lines(2), "line.BC"
    myFac.BuildLine pickedPoints(5), pickedPoints(8), lines(3), "line.EH"
    myFac.BuildLine pickedPoints(6), pickedPoints(7), lines(4), "line.FG"

    ' Update
    myFac.myUpdate

End Sub

Public Sub FixPointsOrder()

    Dim tmpPoint As HybridShapePointCoord

    Dim coords1(2) As Variant
    Dim coords2(2) As Variant
    Dim mtrxData(2, 2) As Double

    Dim pointToGetCoords

    Set pointToGetCoords = pickedPoints(1)
    pointToGetCoords.GetCoordinates coords1

    Set pointToGetCoords = pickedPoints(4)
    pointToGetCoords.GetCoordinates coords2
    mtrxData(0, 0) = coords2(0) - coords1(0)        ' x    of vector 14
    mtrxData(0, 1) = coords2(1) - coords1(1)        ' y    of vector 14
    mtrxData(0, 2) = coords2(2) - coords1(2)        ' z    of vector 14

    Set pointToGetCoords = pickedPoints(2)
    pointToGetCoords.GetCoordinates coords2
    mtrxData(1, 0) = coords2(0) - coords1(0)        ' x    of vector 12
    mtrxData(1, 1) = coords2(1) - coords1(1)        ' y    of vector 12
    mtrxData(1, 2) = coords2(2) - coords1(2)        ' z    of vector 12

    Set pointToGetCoords = pickedPoints(5)
    pointToGetCoords.GetCoordinates coords2
    mtrxData(2, 0) = coords2(0) - coords1(0)        ' x    of vector 15
    mtrxData(2, 1) = coords2(1) - coords1(1)        ' y    of vector 15
    mtrxData(2, 2) = coords2(2) - coords1(2)        ' z    of vector 15

    Dim tmpM As New Matrix
    tmpM.SetDimension 3
    tmpM.SetData mtrxData

    If (tmpM.Det < 0) Then

        ' Remove wrong lines and planes
        myFac.RemovePreConstruct lines(1)
        myFac.RemovePreConstruct lines(2)
        myFac.RemovePreConstruct lines(3)
        myFac.RemovePreConstruct lines(4)

        ' exchange 2 <-> 4 and 6 <-> 8
        'MsgBox "swap2"
        Set tmpPoint = pickedPoints(2)
        Set pickedPoints(2) = pickedPoints(4)
        Set pickedPoints(4) = tmpPoint
        Set tmpPoint = pickedPoints(6)
        Set pickedPoints(6) = pickedPoints(8)
        Set pickedPoints(8) = tmpPoint

        ' Construct new lines and planes
        BuildConstructPre

    End If


End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8
    myFac.BuildPlane3Pt pickedPoints(2), pickedPoints(3), pickedPoints(6), checkPlanes(3), "plane.3.check" '7
    myFac.BuildPlane3Pt pickedPoints(1), pickedPoints(4), pickedPoints(5), checkPlanes(4), "plane.4.check" '8

    ' Update
    myFac.myUpdate

    ' Check planarity of some faces
    formPrimitiveCreator.TextBox2.Text = myFac.GetDistance(checkPlanes(1), pickedPoints(4))
    formPrimitiveCreator.TextBox3.Text = myFac.GetDistance(checkPlanes(2), pickedPoints(8))
    formPrimitiveCreator.TextBox4.Text = myFac.GetDistance(checkPlanes(3), pickedPoints(7))
    formPrimitiveCreator.TextBox5.Text = myFac.GetDistance(checkPlanes(4), pickedPoints(8))

    ' Build all the middle points and lines, connecting them
    myFac.BuildMidPoint2 pickedPoints(1), pickedPoints(4), midPoints(1), "point.mid.1"
    myFac.BuildMidPoint2 pickedPoints(2), pickedPoints(3), midPoints(2), "point.mid.2"
    myFac.BuildMidPoint2 pickedPoints(5), pickedPoints(8), midPoints(3), "point.mid.3"
    myFac.BuildMidPoint2 pickedPoints(6), pickedPoints(7), midPoints(4), "point.mid.4"
    myFac.BuildLine midPoints(1), midPoints(2), lines(5), "line.bottom.mid"
    myFac.BuildLine midPoints(3), midPoints(4), lines(6), "line.top.mid"
    myFac.BuildMidPoint2 midPoints(1), midPoints(2), midPoints(5), "point.mid.5"
    myFac.BuildMidPoint2 midPoints(3), midPoints(4), midPoints(6), "point.mid.6"
    myFac.BuildLine midPoints(5), midPoints(6), lines(7), "line.mid"
    myFac.BuildMidPoint2 midPoints(5), midPoints(6), midPoints(7), "point.center"
    myFac.myUpdate
    ' Build top and botton planes
    myFac.BuildPlane lines(1), lines(2), planes(1), "plane.bottom"
    myFac.BuildPlane lines(3), lines(4), planes(2), "plane.top"

    ' Build Y axis in both planes
    myFac.BuildNormalToLine lines(1), planes(1), midPoints(1), Yaces(1), "line.bottom.Y"
    myFac.BuildNormalToLine lines(3), planes(2), midPoints(3), Yaces(2), "line.top.Y"

    ' Build X axis of the primitive
    myFac.BuildParallelLine lines(1), planes(1), midPoints(7), Xaxis, "XaxisOfThePrimitive"

    ' Build Z axis of the primitive
    myFac.BuildNormalToPlane planes(1), midPoints(7), Zaxis, "ZaxisOfThePrimitive"

    
    ' Update
    myFac.myUpdate

    ' if Z axis of the primitive does not coincide with the middle line of the primitive
    If (Round(myFac.GetAngle(lines(7), Zaxis), TOLERANCE) <> 0 And _
        Round(myFac.GetAngle(lines(7), Zaxis), TOLERANCE) <> 180) Then

        ' Build the plane through the Z axis and the middle line of the primitive
        myFac.BuildPlane lines(7), Zaxis, orientPlane, "plane.orientation"
    
        ' Build ZX plane of the primitive
        myFac.BuildPlane Zaxis, Xaxis, ZXplane, "plane.ZX"

    End If

    myFac.BuildSphere midPoints(7), 1#, s, "sphere.identity"
    myFac.BuildIntersection s, Zaxis, Zorts, "Zorts"
    myFac.BuildIntersection s, Xaxis, Xorts, "Xorts"

    Dim lineCD As HybridShapeLinePtPt
    myFac.BuildLine pickedPoints(3), pickedPoints(4), lineCD, "line.CD"

    myFac.SelectNearestPoint Zorts, planes(2), Zort, "Zort"
    myFac.SelectNearestPoint Xorts, lineCD, Xort, "Xort"
    myFac.BuildPoint Zort, Zort2, "Zort2"
    myFac.BuildPoint Xort, Xort2, "Xort2"

    ' Update
    myFac.myUpdate

    ' Extract axis system of the primitve

    Dim v_pointToExtractCoordinates
    Dim v_tmpVariant(2)
    Dim v_tmpDouble(2) As Double
    Dim v_tmpCenter(2) As Double

    Set v_pointToExtractCoordinates = midPoints(7)
    v_pointToExtractCoordinates.GetCoordinates v_tmpVariant
    v_tmpCenter(0) = v_tmpVariant(0)
    v_tmpCenter(1) = v_tmpVariant(1)
    v_tmpCenter(2) = v_tmpVariant(2)
    mAxisSystem.SetCenter v_tmpCenter    ' Set center of the axis system

    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Z direction of the axis system

    Set v_pointToExtractCoordinates = Xort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetXort v_tmpDouble      ' Set X direction of the axis system

    mAxisSystem.ComputeYort              ' Compute the last Y direction from given Z and X directions

    'Call mAxisSystem.Draw

End Sub

Public Sub Recognize()

    ' Extract parameters of the primitive

    pDx1 = Round(myFac.GetDistance(pickedPoints(1), pickedPoints(4)) / 2#, TOLERANCE)
    pDy1 = Round(myFac.GetDistance(lines(1), lines(2)) / 2#, TOLERANCE)
    pDx2 = Round(myFac.GetDistance(pickedPoints(5), pickedPoints(8)) / 2#, TOLERANCE)
    pDy2 = Round(myFac.GetDistance(lines(3), lines(4)) / 2#, TOLERANCE)
    pDz = Round(myFac.GetDistance(planes(1), planes(2)) / 2#, TOLERANCE)

    formPrimitiveCreator.ListBox1.AddItem "pDx1 = " & Trim(Str(pDx1))
    formPrimitiveCreator.ListBox1.AddItem "pDy1 = " & Trim(Str(pDy1))
    formPrimitiveCreator.ListBox1.AddItem "pDx2 = " & Trim(Str(pDx2))
    formPrimitiveCreator.ListBox1.AddItem "pDy2 = " & Trim(Str(pDy2))
    formPrimitiveCreator.ListBox1.AddItem "pDz = " & Trim(Str(pDz))

End Sub

Public Sub ApplyParametersToUDF(shpInst As ShapeInstance)
    Call shpInst.GetParameter("dx1").ValuateFromString(Trim(Str(pDx1)) + "mm")
    Call shpInst.GetParameter("dy1").ValuateFromString(Trim(Str(pDy1)) + "mm")
    Call shpInst.GetParameter("dx2").ValuateFromString(Trim(Str(pDx2)) + "mm")
    Call shpInst.GetParameter("dy2").ValuateFromString(Trim(Str(pDy2)) + "mm")
    Call shpInst.GetParameter("dz").ValuateFromString(Trim(Str(pDz)) + "mm")
End Sub

Public Sub GetAxisSystem(ByRef o_axSystem As myAxisSystem)
    Set o_axSystem = mAxisSystem
End Sub

Attribute VB_Name = "myTubs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' myTubs class

Option Explicit

Const TOLERANCE = 10

' -- Data members ----------------------------------------------------------------------

Dim pickedPoints(1 To 8) As HybridShapePointCoord

' pointer to singleton myFactory object
Dim myFac As myFactory

' temporary construct element
Dim checkPlanes(1 To 2) As HybridShapePlane3Points
Dim lines(1 To 4) As HybridShapeLinePtPt
Dim centers(1 To 2) As HybridShape 'Intersection
Dim Center As HybridShapePointBetween
Dim planes(1 To 4) As HybridShapePlane2Lines

Dim Zaxis As HybridShape
Dim Yaxis As HybridShapeIntersection
Dim Xaxis As HybridShapeLineAngle
Dim ZXplane As HybridShapePlane2Lines
Dim s As HybridShapeSphere
Dim Zorts As HybridShapeIntersection
Dim Xorts As HybridShapeIntersection
Dim Yorts As HybridShapeIntersection
Dim Zort As HybridShape
Dim Xort As HybridShape
Dim Yort As HybridShape
Dim Zort2 As HybridShape
Dim Xort2 As HybridShape
Dim Yort2 As HybridShape

' recognized parameters
Dim pRmin As Double
Dim pRmax As Double
Dim pDz As Double
Dim pSPhi As Double
Dim pDPhi As Double

' recognized axis system
Dim mAxisSystem As New myAxisSystem

' -- Methods ---------------------------------------------------------------------------

Public Sub SetFactory(ByRef p_fac As myFactory)

    Set myFac = p_fac

End Sub

Public Sub SetPickedPoints(p1 As HybridShapePointCoord, p2 As HybridShapePointCoord, _
                            p3 As HybridShapePointCoord, p4 As HybridShapePointCoord, _
                            p5 As HybridShapePointCoord, p6 As HybridShapePointCoord, _
                            p7 As HybridShapePointCoord, p8 As HybridShapePointCoord)

    Set pickedPoints(1) = p1
    Set pickedPoints(2) = p2
    Set pickedPoints(3) = p3
    Set pickedPoints(4) = p4
    Set pickedPoints(5) = p5
    Set pickedPoints(6) = p6
    Set pickedPoints(7) = p7
    Set pickedPoints(8) = p8

End Sub

Public Sub SetPickedPoints2(pts() As HybridShapePointCoord)

    Me.SetPickedPoints pts(1), pts(2), pts(3), pts(4), pts(5), pts(6), pts(7), pts(8)

End Sub

Public Sub BuildConstructPre()

    myFac.BuildLine pickedPoints(1), pickedPoints(4), lines(1), "line.AD"
    myFac.BuildLine pickedPoints(2), pickedPoints(3), lines(2), "line.BC"
    myFac.BuildLine pickedPoints(5), pickedPoints(8), lines(3), "line.EH"
    myFac.BuildLine pickedPoints(6), pickedPoints(7), lines(4), "line.FG"

    ' Update
    myFac.myUpdate

End Sub

Public Sub FixPointsOrder()


End Sub

Public Sub BuildConstructPost()

    ' Build check planes
    myFac.BuildPlane3Pt pickedPoints(1), pickedPoints(2), pickedPoints(3), checkPlanes(1), "plane.1.check" '4
    myFac.BuildPlane3Pt pickedPoints(5), pickedPoints(6), pickedPoints(7), checkPlanes(2), "plane.2.check" '8

    ' Update
    myFac.myUpdate

    ' Check planarity of the selected groups of points
    formPrimitiveCreator.TextBox2.Text = myFac.GetDistance(checkPlanes(1), pickedPoints(4))
    formPrimitiveCreator.TextBox3.Text = myFac.GetDistance(checkPlanes(2), pickedPoints(8))

    ' Build the center of the primitive in two different ways
    Dim flag As Integer
    flag = 0
    'check if pDPhi=180
    If myFac.GetAngle(lines(2), lines(4)) = 180 Or myFac.GetAngle(lines(2), lines(4)) = 0 Then
      myFac.BuildMidPoint2 pickedPoints(4), pickedPoints(8), centers(1), "center.1" 'bottom
      myFac.BuildMidPoint2 pickedPoints(3), pickedPoints(7), centers(2), "center.2" 'top
      flag = 1
    Else
      myFac.BuildIntersectionPoint lines(1), lines(3), centers(1), "center.1" 'bottom
      myFac.BuildIntersectionPoint lines(2), lines(4), centers(2), "center.2" 'top
    End If
    ' Build bounding planes
    myFac.BuildPlane lines(1), lines(2), planes(3), "plane.1.phi"
    myFac.BuildPlane lines(3), lines(4), planes(4), "plane.2.phi"
    myFac.myUpdate
    
    myFac.BuildMidPoint2 centers(1), centers(2), Center, "center"
    
     myFac.myUpdate
    ' Build axes of the primitive
    myFac.BuildParallelLine lines(1), planes(3), Center, Xaxis, "XaxisOfThePrimitive"
    If flag = 0 Then
        myFac.BuildIntersectionLine planes(3), planes(4), Zaxis, "ZaxisOfThePrimitive"
    Else
        myFac.BuildLine centers(1), centers(2), Zaxis, "ZaxisOfThePrimitive"
        Zaxis.SetLengthType 1
    End If
     myFac.myUpdate
    ' Build YZ plane of the primitive
    myFac.BuildPlane Zaxis, Xaxis, ZXplane, "plane.ZX"
   ' myFac.BuildNormalToPlane YZplane, centers(1), Xaxis, "XaxisOfThePrimitive"

    ' Update
    myFac.myUpdate

    ' Check that the center of the primitive found two different ways is the same within tolerance
    formPrimitiveCreator.TextBox1.Text = myFac.GetDistance(centers(1), centers(2))

    ' Build a sphere, its intersection with the Z axis and 'near' to define the positive direction of the Z axis
    myFac.BuildSphere Center, 1#, s, "sphere.identity"
    myFac.BuildIntersection s, Zaxis, Zorts, "Zorts"
    myFac.BuildIntersection s, Xaxis, Xorts, "Xorts"
   ' myFac.BuildIntersection s, Yaxis, Yorts, "Yorts"
    myFac.SelectNearestPoint Zorts, centers(2), Zort, "Zort"
    myFac.SelectNearestPoint Xorts, lines(1), Xort, "Xort"
   ' myFac.SelectNearestPoint Yorts, lines(1), Yort, "Yort"
    myFac.BuildPoint Zort, Zort2, "Zort2"
    myFac.BuildPoint Xort, Xort2, "Xort2"
   ' myFac.BuildPoint Yort, Yort2, "Yort2"

    ' Update
    myFac.myUpdate
    
    ' Compute coordinate system
    Dim v_pointToExtractCoordinates
    Dim v_tmpVariant(2)
    Dim v_tmpDouble(2) As Double
    Dim v_tmpCenter(2) As Double
    Dim centaxis As HybridShape
    Dim cent
    
    myFac.Center Center, v_tmpCenter
    mAxisSystem.SetCenter v_tmpCenter    ' Set center of the axis system

    Set v_pointToExtractCoordinates = Xort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetXort v_tmpDouble      ' Set Z direction of the axis system

  '  Set v_pointToExtractCoordinates = Yort2
  '  v_pointToExtractCoordinates.GetCoordinates v_tmpVariant
  '  v_tmpDouble(0) = v_tmpVariant(0) - v_tmpCenter(0)
  '  v_tmpDouble(1) = v_tmpVariant(1) - v_tmpCenter(1)
  '  v_tmpDouble(2) = v_tmpVariant(2) - v_tmpCenter(2)
  '  mAxisSystem.SetYort v_tmpDouble      ' Set X direction of the axis system
    
    Set v_pointToExtractCoordinates = Zort2
    v_pointToExtractCoordinates.GetCoordinates v_tmpVariant
    v_tmpDouble(0) = v_tmpVariant(0) - v_tmpCenter(0)
    v_tmpDouble(1) = v_tmpVariant(1) - v_tmpCenter(1)
    v_tmpDouble(2) = v_tmpVariant(2) - v_tmpCenter(2)
    mAxisSystem.SetZort v_tmpDouble      ' Set Y direction of the axis system
    
    mAxisSystem.ComputeYort              ' Compute the last Y direction from given Z and X directions
  ' mAxisSystem.ComputeXort
  ' mAxisSystem.ComputeZort

End Sub

Public Sub Recognize()

    ' Compute pRmin
    Dim Rmin As Double
    Rmin = myFac.GetDistance(centers(1), pickedPoints(4))
    pRmin = Round(Rmin, TOLERANCE)
    formPrimitiveCreator.ListBox1.AddItem "pRmin = " & pRmin

    ' Compute pRmax
    Dim Rmax As Double
    Rmax = myFac.GetDistance(centers(1), pickedPoints(1))
    pRmax = Round(Rmax, TOLERANCE)
    formPrimitiveCreator.ListBox1.AddItem "pRmax = " & pRmax
       
    ' Compute pDz
    Dim Dz As Double
    Dz = myFac.GetDistance(centers(1), centers(2)) / 2#
    pDz = Round(Dz, TOLERANCE)
    formPrimitiveCreator.ListBox1.AddItem "pDz = " & pDz
    
    ' Compute pDPhi
    DPhi = myFac.GetAngle(planes(3), planes(4))
    pDPhi = Round(DPhi, TOLERANCE)
    Call checkDPhi
    myFac.myUpdate
    formPrimitiveCreator.ListBox1.AddItem "pDPhi = " & pDPhi
    
    ' Compute pSPhi
    'Dim SPhi As Double
    'SPhi = DPhi / 2#
    'pSPhi = Round(SPhi, TOLERANCE)
    pSPhi = pDPhi / 2
    formPrimitiveCreator.ListBox1.AddItem "pSPhi = " & pSPhi
  
End Sub
Public Sub GetAxisSystem(ByRef o_axSystem As myAxisSystem)
    Set o_axSystem = mAxisSystem
End Sub
Public Sub ApplyParametersToUDF(shpInst As ShapeInstance)

    Call shpInst.GetParameter("pRMin").ValuateFromString(Trim(Str(pRmin)) + "mm")
    Call shpInst.GetParameter("pRMax").ValuateFromString(Trim(Str(pRmax)) + "mm")
    Call shpInst.GetParameter("pDz").ValuateFromString(Trim(Str(pDz)) + "mm")
    Call shpInst.GetParameter("pDPhi").ValuateFromString(Trim(Str(pDPhi)) + "deg")
    Call shpInst.GetParameter("pSPhi").ValuateFromString(Trim(Str(pSPhi)) + "deg")


End Sub

Public Sub checkDPhi()
    Dim mtrxData(2, 2) As Double
    Dim tmpData(2) As Double

    Dim pointToGetCoords
    Dim coords1(2) As Variant
    Dim coords2(2) As Variant

    Call mAxisSystem.GetZort(tmpData)
    mtrxData(0, 0) = tmpData(0)
    mtrxData(0, 1) = tmpData(1)
    mtrxData(0, 2) = tmpData(2)

    Call mAxisSystem.GetXort(tmpData)
    mtrxData(1, 0) = tmpData(0)
    mtrxData(1, 1) = tmpData(1)
    mtrxData(1, 2) = tmpData(2)
    
    Set pointToGetCoords = pickedPoints(6) 'внешняя верхняя точка
    pointToGetCoords.GetCoordinates coords1
    Set pointToGetCoords = pickedPoints(7) 'внутренняя верхняя точка
    pointToGetCoords.GetCoordinates coords2

    Call mAxisSystem.GetXort(tmpData)
    mtrxData(2, 0) = coords1(0) - coords2(0)
    mtrxData(2, 1) = coords1(1) - coords2(1)
    mtrxData(2, 2) = coords1(2) - coords2(2)

    Dim MatrixZX As New Matrix
    MatrixZX.SetDimension 3
    MatrixZX.SetData mtrxData
               
    Call mAxisSystem.GetYort(tmpData)
    mtrxData(1, 0) = tmpData(0)
    mtrxData(1, 1) = tmpData(1)
    mtrxData(1, 2) = tmpData(2)

    Dim MatrixZY As New Matrix
    MatrixZY.SetDimension 3
    MatrixZY.SetData mtrxData
            
    '>270 + -
    '>180 + +
    '>90 - +
    '>0 - -
    
   
    ' Det of       Det of       Quarter of
' MatrixZX     MatrixZY     Phi angle
'    -            -             I
'    -            +             II
'    +            +             III
'    +            -             IV
    If (pDPhi > 0# And pDPhi <= 90#) Then
        If (MatrixZX.Det > 0#) Then
            If (MatrixZY.Det > 0#) Then
                ' III
                pDPhi = pDPhi + 180#
            Else
                ' IV
                pDPhi = 360# - pDPhi
            End If
        Else
            If (MatrixZY.Det < 0#) Then
                ' I
                'ok
                pDPhi = pDPhi
            Else
                ' II
                pDPhi = 180# - pDPhi
            End If
        End If
    ElseIf (pDPhi > 90# And pDPhi <= 180#) Then
        If (MatrixZX.Det > 0#) Then
            If (MatrixZY.Det > 0#) Then
                ' III
                pDPhi = 360# - pDPhi
            Else
                ' IV
                pDPhi = 180# + pDPhi
            End If
        Else
            If (MatrixZY.Det < 0#) Then
                ' I
                pDPhi = 180# - pDPhi
            Else
                ' II
                pDPhi = pDPhi
            End If
        End If
    ElseIf (pDPhi = 0# Or pDPhi = 180#) Then
            pDPhi = 180#
    Else
        MsgBox "Warning. Strange DPhi computed.", vbExclamation
    End If
   
End Sub
