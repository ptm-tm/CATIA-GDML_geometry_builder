Attribute VB_Name = "BooleanSubs"
Option Explicit

Public Function CreateUnion(op1 As Body, _
                        op2 As Body, _
                        PartDocumentDest As PartDocument, _
                        resName As String) As Body

    Dim PartDest As Part
    Dim shpFactory As ShapeFactory

    Set PartDest = PartDocumentDest.Part
    Set shpFactory = PartDest.ShapeFactory
    Set CreateUnion = PartDest.Bodies.Add

    PartDest.InWorkObject = CreateUnion
    shpFactory.AddNewAssemble op1
    shpFactory.AddNewAdd op2
    CreateUnion.name = resName

End Function

Public Function CreateSubtracion(op1 As Body, _
                        op2 As Body, _
                        PartDocumentDest As PartDocument, _
                        resName As String) As Body

    Dim PartDest As Part
    Dim shpFactory As ShapeFactory

    Set PartDest = PartDocumentDest.Part
    Set shpFactory = PartDest.ShapeFactory
    Set CreateSubtracion = PartDest.Bodies.Add

    PartDest.InWorkObject = CreateSubtracion
    shpFactory.AddNewAssemble op1
    shpFactory.AddNewRemove op2
    CreateSubtracion.name = resName

End Function

Public Function CreateIntersection(op1 As Body, _
                        op2 As Body, _
                        PartDocumentDest As PartDocument, _
                        resName As String) As Body

    Dim PartDest As Part
    Dim shpFactory As ShapeFactory

    Set PartDest = PartDocumentDest.Part
    Set shpFactory = PartDest.ShapeFactory
    Set CreateIntersection = PartDest.Bodies.Add

    PartDest.InWorkObject = CreateIntersection
    shpFactory.AddNewAssemble op1
    shpFactory.AddNewIntersect op2
    CreateIntersection.name = resName

End Function

Attribute VB_Name = "CTimer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private Type LARGE_INTEGER
    lowpart As Long
    highpart As Long
End Type

Private Declare Function QueryPerformanceCounter Lib "kernel32" (lpPerformanceCount As LARGE_INTEGER) As Long
Private Declare Function QueryPerformanceFrequency Lib "kernel32" (lpFrequency As LARGE_INTEGER) As Long

Private m_CounterStart As LARGE_INTEGER
Private m_CounterEnd As LARGE_INTEGER
Private m_crFrequency As Double

Private Const TWO_32 = 4294967296# ' = 256# * 256# * 256# * 256#

Private Function LI2Double(LI As LARGE_INTEGER) As Double
Dim Low As Double
    Low = LI.lowpart
    If Low < 0 Then
        Low = Low + TWO_32
    End If
    LI2Double = LI.highpart * TWO_32 + Low
End Function

Private Sub Class_Initialize()
Dim PerfFrequency As LARGE_INTEGER
    QueryPerformanceFrequency PerfFrequency
    m_crFrequency = LI2Double(PerfFrequency)
End Sub

Public Sub StartCounter()
    QueryPerformanceCounter m_CounterStart
End Sub

Property Get TimeElapsed() As Double
Dim crStart As Double
Dim crStop As Double
    QueryPerformanceCounter m_CounterEnd
    crStart = LI2Double(m_CounterStart)
    crStop = LI2Double(m_CounterEnd)
    TimeElapsed = 1000# * (crStop - crStart) / m_crFrequency
End Property

Attribute VB_Name = "CommonDigitalString"
Option Explicit

Public Function unitConvert(unit As String) As Double

    Dim PI As Double
    PI = 3.14159265358979
    Select Case unit
        Case "mm"
            unitConvert = 1#
        Case "cm"
            unitConvert = 10#
        Case "m"
            unitConvert = 1000#
        Case "deg"
            unitConvert = 1#
        Case "degree"
            unitConvert = 1#
        Case "radian"
            unitConvert = 180# / PI
        Case "rad"
            unitConvert = 180# / PI
    End Select

End Function

Public Function isNum(str As String) As Boolean

    Dim i As Integer
    Dim flag As Boolean
    flag = False
    isNum = True
    For i = 1 To Len(str)
        If isDigit(Mid(str, i, 1)) = False Then
            isNum = False
        End If
    Next

End Function

Public Function isDigit(str As String) As Boolean

    Dim arr(0 To 9) As String
    Dim i As Integer
    arr(0) = "0"
    arr(1) = "1"
    arr(2) = "2"
    arr(3) = "3"
    arr(4) = "4"
    arr(5) = "5"
    arr(6) = "6"
    arr(7) = "7"
    arr(8) = "8"
    arr(9) = "9"
    isDigit = False
    For i = 0 To 9
        If str = arr(i) Then
            isDigit = True
        End If
    Next

End Function

Attribute VB_Name = "Elements"
Option Explicit

Dim NonExpNumberRegExp As New RegExp
Dim ExpNumberRegExp As New RegExp

Public Sub InitRegexp()
    NonExpNumberRegExp.Pattern = "^(\+|-)?(\d*\.)?\d*$"
    ExpNumberRegExp.Pattern = "^(\+|-)?(\d*\.)?\d*(e|E)(\+|-)?(\d)+$"
End Sub

' Checks whether the input string is a number - standard or exp form
Public Function CheckIsNumber(paramStr As String) As Boolean

    CheckIsNumber = False

    ' Check that the parameter string is just a number without letters
    If (NonExpNumberRegExp.Test(paramStr)) Then
        CheckIsNumber = True
        Exit Function
    End If

    ' The number written using the exponential form contains letters but does not require formula
    ' So check whether the parameter string is an exp-number and if so, uncheck the flag
    If (ExpNumberRegExp.Test(paramStr)) Then
        CheckIsNumber = True
    End If

End Function

Public Sub CreateFormula(PartDest As Part, _
                    paramStr As String, _
                    param As Parameter, _
                    rels As Relations, _
                    paramName As String)

    paramStr = Trim(paramStr)

    If (CheckIsNumber(paramStr)) Then
        Exit Sub
    End If

    ' Catch specific cases
    ' such as "0" or "(0)" or "-(0)"
    ' TODO

    ' Otherwise - formula

    'Определение типа параметра length|angle
    'переделать чтобы это нормально выглядело
    Dim parType As String
    If (paramName = "_pSPhi" Or paramName = "_pDPhi" Or paramName = "_alpha" _
            Or paramName = "_theta" Or paramName = "_phi" Or paramName = "_pSTheta" _
            Or paramName = "_pDTheta" Or paramName = "_pTheta" Or paramName = "_pPhi" _
            Or paramName = "_pAlp1" Or paramName = "_rotX" Or paramName = "_rotY" Or paramName = "_rotZ") Then
        parType = "angle"
    Else
        parType = "length"
    End If
    
    Dim form As Formula
    paramStr = parseFormula(paramStr, parType)
    
    If (paramName = "_rotZ" Or paramName = "_rotY" Or paramName = "_rotX") Then
        paramStr = "-(" & paramStr & ")"
    End If
    
    Set form = rels.CreateFormula(PartDest.name & paramName, "", param, paramStr)

End Sub

Public Sub CreateFormula2(PartDest As Part, _
                    paramStr As String, _
                    paramPath As String, _
                    rels As Relations, _
                    paramName As String, _
                    params As Parameters)

    paramStr = Trim(paramStr)

    If (CheckIsNumber(paramStr)) Then
        Exit Sub
    End If

    ' Catch specific cases
    ' such as "0" or "(0)" or "-(0)"
    ' TODO

    ' Otherwise - formula

    'Определение типа параметра length|angle
    'переделать чтобы это нормально выглядело
    Dim parType As String
    If (paramName = "_pSPhi" Or paramName = "_pDPhi" Or paramName = "_alpha" _
            Or paramName = "_theta" Or paramName = "_phi" Or paramName = "_pSTheta" _
            Or paramName = "_pDTheta" Or paramName = "_pTheta" Or paramName = "_pPhi" _
            Or paramName = "_pAlp1" Or paramName = "_rotX" Or paramName = "_rotY" Or paramName = "_rotZ") Then
        parType = "angle"
    Else
        parType = "length"
    End If
    
    Dim form As Formula
    paramStr = parseFormula(paramStr, parType)
    
    If (paramName = "_rotZ" Or paramName = "_rotY" Or paramName = "_rotX") Then
        paramStr = "-(" & paramStr & ")"
    End If
    
    Set form = rels.CreateFormula(PartDest.name & paramName, "", params.Item(paramPath), paramStr)

End Sub

Public Function CreateArb8(path As String, _
                    PartDocumentDest As PartDocument, _
                    v1x As String, v1y As String, _
                    v2x As String, v2y As String, _
                    v3x As String, v3y As String, _
                    v4x As String, v4y As String, _
                    v5x As String, v5y As String, _
                    v6x As String, v6y As String, _
                    v7x As String, v7y As String, _
                    v8x As String, v8y As String, _
                    dz As String, _
                    lunit As String) As Body

    Dim PartDest As Part
    Dim InsFactory As InstanceFactory
    Dim MyInstance 'As HybridShapeInstance
    Set PartDest = PartDocumentDest.Part
    Set CreateArb8 = PartDest.Bodies.Add
    PartDest.InWorkObject = CreateArb8
    Set InsFactory = PartDest.GetCustomerFactory("InstanceFactory")

    Dim XYPlane As Object
    Dim param(1 To 17) As Parameter

    Call InsFactory.BeginInstanceFactory("G4Arb8_2", (path & "\G4Arb8_2.CATPart"))
    InsFactory.BeginInstantiate

    Set XYPlane = PartDest.FindObjectByName("xy plane")
    InsFactory.PutInputData "xy plane", XYPlane

    Set param(1) = InsFactory.GetParameter("v1x")
    Set param(2) = InsFactory.GetParameter("v1y")
    Set param(3) = InsFactory.GetParameter("v2x")
    Set param(4) = InsFactory.GetParameter("v2y")
    Set param(5) = InsFactory.GetParameter("v3x")
    Set param(6) = InsFactory.GetParameter("v3y")
    Set param(7) = InsFactory.GetParameter("v4x")
    Set param(8) = InsFactory.GetParameter("v4y")
    Set param(9) = InsFactory.GetParameter("v5x")
    Set param(10) = InsFactory.GetParameter("v5y")
    Set param(11) = InsFactory.GetParameter("v6x")
    Set param(12) = InsFactory.GetParameter("v6y")
    Set param(13) = InsFactory.GetParameter("v7x")
    Set param(14) = InsFactory.GetParameter("v7y")
    Set param(15) = InsFactory.GetParameter("v8x")
    Set param(16) = InsFactory.GetParameter("v8y")
    Set param(17) = InsFactory.GetParameter("dz")

    param(1).ValuateFromString (str(Val(Trim(v1x)) * unitConvert(lunit)) & "mm")
    param(2).ValuateFromString (str(Val(Trim(v1y)) * unitConvert(lunit)) & "mm")
    param(3).ValuateFromString (str(Val(Trim(v2x)) * unitConvert(lunit)) & "mm")
    param(4).ValuateFromString (str(Val(Trim(v2y)) * unitConvert(lunit)) & "mm")
    param(5).ValuateFromString (str(Val(Trim(v3x)) * unitConvert(lunit)) & "mm")
    param(6).ValuateFromString (str(Val(Trim(v3y)) * unitConvert(lunit)) & "mm")
    param(7).ValuateFromString (str(Val(Trim(v4x)) * unitConvert(lunit)) & "mm")
    param(8).ValuateFromString (str(Val(Trim(v4y)) * unitConvert(lunit)) & "mm")
    param(9).ValuateFromString (str(Val(Trim(v5x)) * unitConvert(lunit)) & "mm")
    param(10).ValuateFromString (str(Val(Trim(v5y)) * unitConvert(lunit)) & "mm")
    param(11).ValuateFromString (str(Val(Trim(v6x)) * unitConvert(lunit)) & "mm")
    param(12).ValuateFromString (str(Val(Trim(v6y)) * unitConvert(lunit)) & "mm")
    param(13).ValuateFromString (str(Val(Trim(v7x)) * unitConvert(lunit)) & "mm")
    param(14).ValuateFromString (str(Val(Trim(v7y)) * unitConvert(lunit)) & "mm")
    param(15).ValuateFromString (str(Val(Trim(v8x)) * unitConvert(lunit)) & "mm")
    param(16).ValuateFromString (str(Val(Trim(v8y)) * unitConvert(lunit)) & "mm")
    param(17).ValuateFromString (str(Val(Trim(dz)) * unitConvert(lunit)) & "mm")

    Set MyInstance = InsFactory.Instantiate
    InsFactory.EndInstantiate
    InsFactory.EndInstanceFactory

End Function

Public Function CreateBox(path As String, _
                    PartDocumentDest As PartDocument, _
                    pX As String, _
                    pY As String, _
                    pZ As String, _
                    lunit As String) As Body

    Dim PartDest As Part
    Dim InsFactory As InstanceFactory
    Dim MyInstance 'As HybridShapeInstance
    Set PartDest = PartDocumentDest.Part
    Set CreateBox = PartDest.Bodies.Add
    PartDest.InWorkObject = CreateBox
    Set InsFactory = PartDest.GetCustomerFactory("InstanceFactory")

    Dim XYPlane As Object
    Dim param1 As Parameter
    Dim param2 As Parameter
    Dim param3 As Parameter

    Call InsFactory.BeginInstanceFactory("G4Box", (path & "\G4Box.CATPart"))
    InsFactory.BeginInstantiate

    Set XYPlane = PartDest.FindObjectByName("xy plane")
    InsFactory.PutInputData "xy plane", XYPlane

    Set param1 = InsFactory.GetParameter("pX")
    Set param2 = InsFactory.GetParameter("pY")
    Set param3 = InsFactory.GetParameter("pZ")

    If (Right(pX, 3) = ")*2" And Left(pX, 1) = "(") Then
        pX = Mid(pX, 2, Len(pX) - 4)
        param1.ValuateFromString (str(Val(Trim(pX)) * unitConvert(lunit)) & "mm")
    Else
        param1.ValuateFromString (str(Val(Trim(pX)) * unitConvert(lunit) / 2#) & "mm")
    End If
    If (Right(pY, 3) = ")*2" And Left(pY, 1) = "(") Then
        pY = Mid(pY, 2, Len(pY) - 4)
        param2.ValuateFromString (str(Val(Trim(pY)) * unitConvert(lunit)) & "mm")
    Else
        param2.ValuateFromString (str(Val(Trim(pY)) * unitConvert(lunit) / 2#) & "mm")
    End If
    If (Right(pZ, 3) = ")*2" And Left(pZ, 1) = "(") Then
        pZ = Mid(pZ, 2, Len(pZ) - 4)
        param3.ValuateFromString (str(Val(Trim(pZ)) * unitConvert(lunit)) & "mm")
    Else
        param3.ValuateFromString (str(Val(Trim(pZ)) * unitConvert(lunit) / 2#) & "mm")
    End If

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pX, param1, rels, "_pX"
    CreateFormula PartDest, pY, param2, rels, "_pY"
    CreateFormula PartDest, pZ, param3, rels, "_pZ"

    Set MyInstance = InsFactory.Instantiate
    InsFactory.EndInstantiate
    InsFactory.EndInstanceFactory

End Function

Public Function CreateCons(path As String, _
                    PartDocumentDest As PartDocument, _
                    pRmin1 As String, _
                    pRmax1 As String, _
                    pRmin2 As String, _
                    pRmax2 As String, _
                    pDz As String, _
                    pSPhi As String, _
                    pDPhi As String, _
                    lunit As String, _
                    aunit As String, _
                    isForPolycone As Boolean) As Body

    Dim PartDest As Part
    Dim InsFactory As InstanceFactory
    Dim MyInstance 'As HybridShapeInstance
    Set PartDest = PartDocumentDest.Part

    If isForPolycone = False Then
        Set CreateCons = PartDest.Bodies.Add
        PartDest.InWorkObject = CreateCons
    End If

    Set InsFactory = PartDest.GetCustomerFactory("InstanceFactory")

    Dim ZXPlane As Object
    Dim param1 As Parameter
    Dim param2 As Parameter
    Dim param3 As Parameter
    Dim param4 As Parameter
    Dim param5 As Parameter
    Dim param6 As Parameter
    Dim param7 As Parameter

    Call InsFactory.BeginInstanceFactory("G4Cons", (path & "\G4Cons.CATPart"))
    InsFactory.BeginInstantiate

    Set ZXPlane = PartDest.FindObjectByName("zx plane")
    InsFactory.PutInputData "zx plane", ZXPlane

    Set param1 = InsFactory.GetParameter("pRmin1")
    Set param2 = InsFactory.GetParameter("pRmax1")
    Set param3 = InsFactory.GetParameter("pRmin2")
    Set param4 = InsFactory.GetParameter("pRmax2")
    Set param5 = InsFactory.GetParameter("pDz")
    Set param6 = InsFactory.GetParameter("pSPhi")
    Set param7 = InsFactory.GetParameter("pDPhi")

    If (Right(pDz, 3) = ")*2" And Left(pDz, 1) = "(") Then
        pDz = Mid(pDz, 2, Len(pDz) - 4)
        param5.ValuateFromString (str(Val(Trim(pDz)) * unitConvert(lunit)) & "mm")
    Else
        param5.ValuateFromString (str(Val(Trim(pDz)) * unitConvert(lunit) / 2#) & "mm")
    End If

    param1.ValuateFromString (str(Val(Trim(pRmin1)) * unitConvert(lunit)) & "mm")
    param2.ValuateFromString (str(Val(Trim(pRmax1)) * unitConvert(lunit)) & "mm")
    param3.ValuateFromString (str(Val(Trim(pRmin2)) * unitConvert(lunit)) & "mm")
    param4.ValuateFromString (str(Val(Trim(pRmax2)) * unitConvert(lunit)) & "mm")

    param6.ValuateFromString (str(Val(Trim(pSPhi)) * unitConvert(aunit)) & "deg")
    param7.ValuateFromString (str(Val(Trim(pDPhi)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmin1, param1, rels, "_pRmin1"
    CreateFormula PartDest, pRmax1, param2, rels, "_pRmax1"
    CreateFormula PartDest, pRmin2, param3, rels, "_pRmin2"
    CreateFormula PartDest, pRmax2, param4, rels, "_pRmax2"
    CreateFormula PartDest, pDz, param5, rels, "_pDz"
    CreateFormula PartDest, pSPhi, param6, rels, "_pSPhi"
    CreateFormula PartDest, pDPhi, param7, rels, "_pDPhi"

    Set MyInstance = InsFactory.Instantiate
    InsFactory.EndInstantiate
    InsFactory.EndInstanceFactory

    If isForPolycone = True Then
        MyInstance.name = "PolyconePiece." & Mid(MyInstance.name, 8)
    End If

End Function

Public Function CreateEllipsoid(path As String, _
                        PartDocumentDest As PartDocument, _
                        pxSemiAxis As String, _
                        pySemiAxis As String, _
                        pzSemiAxis As String, _
                        pzBottomCut As String, _
                        pzTopCut As String, _
                        lunit As String) As Body

    Dim PartDest As Part
    Dim InsFactory As InstanceFactory
    Dim MyInstance 'As HybridShapeInstance
    Set PartDest = PartDocumentDest.Part
    Set CreateEllipsoid = PartDest.Bodies.Add
    PartDest.InWorkObject = CreateEllipsoid
    Set InsFactory = PartDest.GetCustomerFactory("InstanceFactory")

    Dim YZPlane As Object
    Dim ZXPlane As Object
    Dim XYPlane As Object
    Dim param1 As Parameter
    Dim param2 As Parameter
    Dim param3 As Parameter
    Dim param4 As Parameter
    Dim param5 As Parameter

    Call InsFactory.BeginInstanceFactory("G4Ellipsoid", (path & "\G4Ellipsoid.CATPart"))
    InsFactory.BeginInstantiate

    Set YZPlane = PartDest.FindObjectByName("yz plane")
    Set ZXPlane = PartDest.FindObjectByName("zx plane")
    Set XYPlane = PartDest.FindObjectByName("xy plane")
    InsFactory.PutInputData "yz plane", YZPlane
    InsFactory.PutInputData "zx plane", ZXPlane
    InsFactory.PutInputData "xy plane", XYPlane

    Set param1 = InsFactory.GetParameter("pxSemiAxis")
    Set param2 = InsFactory.GetParameter("pySemiAxis")
    Set param3 = InsFactory.GetParameter("pzSemiAxis")
    Set param4 = InsFactory.GetParameter("pzBottomCut")
    Set param5 = InsFactory.GetParameter("pzTopCut")

    param1.ValuateFromString (str(Val(Trim(pxSemiAxis)) * unitConvert(lunit)) & "mm")
    param2.ValuateFromString (str(Val(Trim(pySemiAxis)) * unitConvert(lunit)) & "mm")
    param3.ValuateFromString (str(Val(Trim(pzSemiAxis)) * unitConvert(lunit)) & "mm")
    param4.ValuateFromString (str(Val(Trim(pzBottomCut)) * unitConvert(lunit)) & "mm")
    param5.ValuateFromString (str(Val(Trim(pzTopCut)) * unitConvert(lunit)) & "mm")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pxSemiAxis, param1, rels, "_pxSemiAxis"
    CreateFormula PartDest, pySemiAxis, param2, rels, "_pySemiAxis"
    CreateFormula PartDest, pzSemiAxis, param3, rels, "_pzSemiAxis"
    CreateFormula PartDest, pzBottomCut, param4, rels, "_pzBottomCut"
    CreateFormula PartDest, pzTopCut, param5, rels, "_pzTopCut"

    Set MyInstance = InsFactory.Instantiate
    InsFactory.EndInstantiate
    InsFactory.EndInstanceFactory

End Function

Public Function CreateEllipticalCone(path As String, _
                                PartDocumentDest As PartDocument, _
                                pxSemiAxis As String, _
                                pySemiAxis As String, _
                                zMax As String, _
                                pzTopCut As String, _
                                lunit As String) As Body

    Dim PartDest As Part
    Dim InsFactory As InstanceFactory
    Dim MyInstance 'As HybridShapeInstance
    Set PartDest = PartDocumentDest.Part
    Set CreateEllipticalCone = PartDest.Bodies.Add
    PartDest.InWorkObject = CreateEllipticalCone
    Set InsFactory = PartDest.GetCustomerFactory("InstanceFactory")

    Dim YZPlane As Object
    Dim ZXPlane As Object
    Dim param1 As Parameter
    Dim param2 As Parameter
    Dim param3 As Parameter
    Dim param4 As Parameter

    Call InsFactory.BeginInstanceFactory("G4EllipticalCone", (path & "\G4EllipticalCone.CATPart"))
    InsFactory.BeginInstantiate
    Set YZPlane = PartDest.FindObjectByName("yz plane")
    Set ZXPlane = PartDest.FindObjectByName("zx plane")
    InsFactory.PutInputData "yz plane", YZPlane
    InsFactory.PutInputData "zx plane", ZXPlane

    Set param1 = InsFactory.GetParameter("pxSemiAxis")
    Set param2 = InsFactory.GetParameter("pySemiAxis")
    Set param3 = InsFactory.GetParameter("zMax")
    Set param4 = InsFactory.GetParameter("pzTopCut")

    param1.ValuateFromString (str(Val(Trim(pxSemiAxis)) * unitConvert(lunit)) & "mm")
    param2.ValuateFromString (str(Val(Trim(pySemiAxis)) * unitConvert(lunit)) & "mm")
    param3.ValuateFromString (str(Val(Trim(zMax)) * unitConvert(lunit)) & "mm")
    param4.ValuateFromString (str(Val(Trim(pzTopCut)) * unitConvert(lunit)) & "mm")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pxSemiAxis, param1, rels, "_pxSemiAxis"
    CreateFormula PartDest, pySemiAxis, param2, rels, "_pySemiAxis"
    CreateFormula PartDest, zMax, param3, rels, "_zMax"
    CreateFormula PartDest, pzTopCut, param4, rels, "_pzTopCut"

    Set MyInstance = InsFactory.Instantiate
    InsFactory.EndInstantiate
    InsFactory.EndInstanceFactory

End Function

Public Function CreateEllipticalTube(path As String, _
                                PartDocumentDest As PartDocument, _
                                Dx As String, _
                                Dy As String, _
                                dz As String, _
                                lunit As String) As Body

    Dim PartDest As Part
    Dim InsFactory As InstanceFactory
    Dim MyInstance 'As HybridShapeInstance
    Set PartDest = PartDocumentDest.Part
    Set CreateEllipticalTube = PartDest.Bodies.Add
    PartDest.InWorkObject = CreateEllipticalTube
    Set InsFactory = PartDest.GetCustomerFactory("InstanceFactory")

    Dim XYPlane As Object
    Dim param1 As Parameter
    Dim param2 As Parameter
    Dim param3 As Parameter

    Call InsFactory.BeginInstanceFactory("G4EllipticalTube", (path & "\G4EllipticalTube.CATPart"))
    InsFactory.BeginInstantiate
    Set XYPlane = PartDest.FindObjectByName("xy plane")
    InsFactory.PutInputData "xy plane", XYPlane

    Set param1 = InsFactory.GetParameter("Dx")
    Set param2 = InsFactory.GetParameter("Dy")
    Set param3 = InsFactory.GetParameter("Dz")

    param1.ValuateFromString (str(Val(Trim(Dx)) * unitConvert(lunit)) & "mm")
    param2.ValuateFromString (str(Val(Trim(Dy)) * unitConvert(lunit)) & "mm")
    param3.ValuateFromString (str(Val(Trim(dz)) * unitConvert(lunit)) & "mm")


    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, Dx, param1, rels, "_Dx"
    CreateFormula PartDest, Dy, param2, rels, "_Dy"
    CreateFormula PartDest, dz, param3, rels, "_Dz"

    Set MyInstance = InsFactory.Instantiate
    InsFactory.EndInstantiate
    InsFactory.EndInstanceFactory

End Function

Public Function CreateHedra(path As String, _
                    PartDocumentDest As PartDocument, _
                    pRmin1 As String, _
                    pRmax1 As String, _
                    pRmin2 As String, _
                    pRmax2 As String, _
                    pDz As String, _
                    pSPhi As String, _
                    pDPhi As String, _
                    numSide As String, _
                    lunit As String, _
                    aunit As String, _
                    isForPolyhedra As Boolean) As Body

    Dim PartDest As Part
    Dim InsFactory As InstanceFactory
    Dim MyInstance 'As HybridShapeInstance
    Set PartDest = PartDocumentDest.Part

    If isForPolyhedra = False Then
        Set CreateHedra = PartDest.Bodies.Add
        PartDest.InWorkObject = CreateHedra
    End If

    Set InsFactory = PartDest.GetCustomerFactory("InstanceFactory")

    Dim XYPlane As Object
    Dim param1 As Parameter
    Dim param2 As Parameter
    Dim param3 As Parameter
    Dim param4 As Parameter
    Dim param5 As Parameter
    Dim param6 As Parameter
    Dim param7 As Parameter
    Dim param8 As Parameter

    Call InsFactory.BeginInstanceFactory("G4Hedra", (path & "\G4Hedra.CATPart"))
    InsFactory.BeginInstantiate

    Set XYPlane = PartDest.FindObjectByName("xy plane")
    InsFactory.PutInputData "xy plane", XYPlane

    Set param1 = InsFactory.GetParameter("pRmin1")
    Set param2 = InsFactory.GetParameter("pRmax1")
    Set param3 = InsFactory.GetParameter("pRmin2")
    Set param4 = InsFactory.GetParameter("pRmax2")
    Set param5 = InsFactory.GetParameter("pDz")
    Set param6 = InsFactory.GetParameter("pSPhi")
    Set param7 = InsFactory.GetParameter("pDPhi")
    Set param8 = InsFactory.GetParameter("numSide")

    If (Right(pDz, 3) = ")*2" And Left(pDz, 1) = "(") Then
        pDz = Mid(pDz, 2, Len(pDz) - 4)
        param5.ValuateFromString (str(Val(Trim(pDz)) * unitConvert(lunit)) & "mm")
    Else
        param5.ValuateFromString (str(Val(Trim(pDz)) * unitConvert(lunit) / 2#) & "mm")
    End If

    param1.ValuateFromString (str(Val(Trim(pRmin1)) * unitConvert(lunit)) & "mm")
    param2.ValuateFromString (str(Val(Trim(pRmax1)) * unitConvert(lunit)) & "mm")
    param3.ValuateFromString (str(Val(Trim(pRmin2)) * unitConvert(lunit)) & "mm")
    param4.ValuateFromString (str(Val(Trim(pRmax2)) * unitConvert(lunit)) & "mm")
    param6.ValuateFromString (str(Val(Trim(pSPhi)) * unitConvert(aunit)) & "deg")
    param7.ValuateFromString (str(Val(Trim(pDPhi)) * unitConvert(aunit)) & "deg")
    param8.ValuateFromString str(Val(Trim(numSide)))

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmin1, param1, rels, "_pRmin1"
    CreateFormula PartDest, pRmax1, param2, rels, "_pRmax1"
    CreateFormula PartDest, pRmin2, param3, rels, "_pRmin2"
    CreateFormula PartDest, pRmax2, param4, rels, "_pRmax2"
    CreateFormula PartDest, pDz, param5, rels, "_pDz"
    CreateFormula PartDest, pSPhi, param6, rels, "_pSPhi"
    CreateFormula PartDest, pDPhi, param7, rels, "_pDPhi"
    CreateFormula PartDest, numSide, param8, rels, "_numSide"

    Set MyInstance = InsFactory.Instantiate
    InsFactory.EndInstantiate
    InsFactory.EndInstanceFactory

    If isForPolyhedra = True Then
        MyInstance.name = "PolyhedraPiece." & Mid(MyInstance.name, 9)
    End If

End Function

Public Function CreateOrb(path As String, _
                    PartDocumentDest As PartDocument, _
                    pRmax As String, _
                    lunit As String) As Body

    Dim PartDest As Part
    Dim InsFactory As InstanceFactory
    Dim MyInstance 'As HybridShapeInstance
    Set PartDest = PartDocumentDest.Part
    Set CreateOrb = PartDest.Bodies.Add
    PartDest.InWorkObject = CreateOrb
    Set InsFactory = PartDest.GetCustomerFactory("InstanceFactory")

    Dim ZXPlane As Object
    Dim param1 As Parameter

    Call InsFactory.BeginInstanceFactory("G4Orb", (path & "\G4Orb.CATPart"))
    InsFactory.BeginInstantiate
    Set ZXPlane = PartDest.FindObjectByName("zx plane")
    InsFactory.PutInputData "zx plane", ZXPlane

    Set param1 = InsFactory.GetParameter("pRmax")

    param1.ValuateFromString (str(Val(Trim(pRmax)) * unitConvert(lunit)) & "mm")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmax, param1, rels, "_pRmax"

    Set MyInstance = InsFactory.Instantiate
    InsFactory.EndInstantiate
    InsFactory.EndInstanceFactory

End Function

Public Function CreatePara(path As String, _
                                PartDocumentDest As PartDocument, _
                                Dx As String, _
                                Dy As String, _
                                dz As String, _
                                alpha As String, _
                                theta As String, _
                                phi As String, _
                                lunit As String, _
                                aunit As String) As Body

    Dim PartDest As Part
    Dim InsFactory As InstanceFactory
    Dim MyInstance 'As HybridShapeInstance
    Set PartDest = PartDocumentDest.Part
    Set CreatePara = PartDest.Bodies.Add
    PartDest.InWorkObject = CreatePara
    Set InsFactory = PartDest.GetCustomerFactory("InstanceFactory")

    Dim ZXPlane As Object
    Dim XYPlane As Object
    Dim param1 As Parameter
    Dim param2 As Parameter
    Dim param3 As Parameter
    Dim param4 As Parameter
    Dim param5 As Parameter
    Dim param6 As Parameter

    Call InsFactory.BeginInstanceFactory("G4Para", (path & "\G4Para.CATPart"))
    InsFactory.BeginInstantiate
    Set ZXPlane = PartDest.FindObjectByName("zx plane")
    Set XYPlane = PartDest.FindObjectByName("xy plane")
    InsFactory.PutInputData "zx plane", ZXPlane
    InsFactory.PutInputData "xy plane", XYPlane

    Set param1 = InsFactory.GetParameter("dx")
    Set param2 = InsFactory.GetParameter("dy")
    Set param3 = InsFactory.GetParameter("dz")
    Set param4 = InsFactory.GetParameter("alpha")
    Set param5 = InsFactory.GetParameter("theta")
    Set param6 = InsFactory.GetParameter("phi")

    If (Right(Dx, 3) = ")*2" And Left(Dx, 1) = "(") Then
        Dx = Mid(Dx, 2, Len(Dx) - 4)
        param1.ValuateFromString (str(Val(Trim(Dx)) * unitConvert(lunit)) & "mm")
    Else
        param1.ValuateFromString (str(Val(Trim(Dx)) * unitConvert(lunit) / 2#) & "mm")
    End If
    If (Right(Dy, 3) = ")*2" And Left(Dy, 1) = "(") Then
        Dy = Mid(Dy, 2, Len(Dy) - 4)
        param2.ValuateFromString (str(Val(Trim(Dy)) * unitConvert(lunit)) & "mm")
    Else
        param2.ValuateFromString (str(Val(Trim(Dy)) * unitConvert(lunit) / 2#) & "mm")
    End If
    If (Right(dz, 3) = ")*2" And Left(dz, 1) = "(") Then
        dz = Mid(dz, 2, Len(dz) - 4)
        param3.ValuateFromString (str(Val(Trim(dz)) * unitConvert(lunit)) & "mm")
    Else
        param3.ValuateFromString (str(Val(Trim(dz)) * unitConvert(lunit) / 2#) & "mm")
    End If

    param4.ValuateFromString (str(Val(Trim(alpha)) * unitConvert(aunit)) & "deg")
    param5.ValuateFromString (str(Val(Trim(theta)) * unitConvert(aunit)) & "deg")
    param6.ValuateFromString (str(Val(Trim(phi)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, Dx, param1, rels, "_Dx"
    CreateFormula PartDest, Dy, param2, rels, "_Dy"
    CreateFormula PartDest, dz, param3, rels, "_Dz"
    CreateFormula PartDest, alpha, param4, rels, "_alpha"
    CreateFormula PartDest, theta, param5, rels, "_theta"
    CreateFormula PartDest, phi, param6, rels, "_phi"

    Set MyInstance = InsFactory.Instantiate
    InsFactory.EndInstantiate
    InsFactory.EndInstanceFactory

End Function

Public Function CreatePolycone(path As String, _
                        PartDocumentDest As PartDocument, _
                        pconXMLNode As IXMLDOMNode) As Body

    Dim i As Integer
    Dim cur_rmin1 As String
    Dim cur_rmin2 As String
    Dim cur_rmax1 As String
    Dim cur_rmax2 As String
    Dim cur_dz As String
    Dim next_dz As Double
    Dim cur_shift As String

    Dim PartDest As Part
    Dim InsFactory As InstanceFactory
    Dim MyInstance 'As HybridShapeInstance
    Set PartDest = PartDocumentDest.Part
    Set CreatePolycone = PartDest.Bodies.Add
    PartDest.InWorkObject = CreatePolycone
    Set InsFactory = PartDest.GetCustomerFactory("InstanceFactory")

    'ReorderList pconXMLNode

    For i = 1 To pconXMLNode.childNodes.Length - 1

        cur_dz = str((Val(pconXMLNode.childNodes.Item(i).Attributes.getNamedItem("z").nodeValue) - _
                      Val(pconXMLNode.childNodes.Item(i - 1).Attributes.getNamedItem("z").nodeValue)))
        cur_rmin1 = pconXMLNode.childNodes.Item(i - 1).Attributes.getNamedItem("rmin").nodeValue
        cur_rmax1 = pconXMLNode.childNodes.Item(i - 1).Attributes.getNamedItem("rmax").nodeValue
        cur_rmin2 = pconXMLNode.childNodes.Item(i).Attributes.getNamedItem("rmin").nodeValue
        cur_rmax2 = pconXMLNode.childNodes.Item(i).Attributes.getNamedItem("rmax").nodeValue

        If i < pconXMLNode.childNodes.Length - 1 Then
            next_dz = (Val(pconXMLNode.childNodes.Item(i + 1).Attributes.getNamedItem("z").nodeValue) - _
                       Val(pconXMLNode.childNodes.Item(i).Attributes.getNamedItem("z").nodeValue))
        End If

        If Val(cur_dz) = 0 Then
            GoTo label
        End If

        CreateCons path, PartDocumentDest, cur_rmin1, cur_rmax1, cur_rmin2, cur_rmax2, cur_dz, _
                                pconXMLNode.Attributes.getNamedItem("startphi").nodeValue, _
                                pconXMLNode.Attributes.getNamedItem("deltaphi").nodeValue, _
                                pconXMLNode.Attributes.getNamedItem("lunit").nodeValue, _
                                pconXMLNode.Attributes.getNamedItem("aunit").nodeValue, True

        If i < pconXMLNode.childNodes.Length - 1 Then
            If next_dz = 0 Then
                cur_shift = str(-(Val(pconXMLNode.childNodes.Item(i + 2).Attributes.getNamedItem("z").nodeValue) - _
                                  Val(pconXMLNode.childNodes.Item(i - 1).Attributes.getNamedItem("z").nodeValue)) / 2#)
            Else
                cur_shift = str(-(Val(pconXMLNode.childNodes.Item(i + 1).Attributes.getNamedItem("z").nodeValue) - _
                                  Val(pconXMLNode.childNodes.Item(i - 1).Attributes.getNamedItem("z").nodeValue)) / 2#)
            End If
        Else
            'cur_shift = str((Val(pconXMLNode.childNodes.Item(i - 1).Attributes.getNamedItem("z").nodeValue) - _
                            Val(pconXMLNode.childNodes.Item(0).Attributes.getNamedItem("z").nodeValue)) / 2#)
            cur_shift = str((Val(pconXMLNode.childNodes.Item(i).Attributes.getNamedItem("z").nodeValue) + _
                          Val(pconXMLNode.childNodes.Item(i - 1).Attributes.getNamedItem("z").nodeValue)) / 2#)
        End If

        CreateShift PartDocumentDest, "0", "0", cur_shift, pconXMLNode.Attributes.getNamedItem("lunit").nodeValue
label:
    Next i

End Function

Public Function CreatePolyhedra(path As String, _
                        PartDocumentDest As PartDocument, _
                        phedraXMLNode As IXMLDOMNode) As Body

    Dim i As Integer
    Dim cur_rmin1 As String
    Dim cur_rmin2 As String
    Dim cur_rmax1 As String
    Dim cur_rmax2 As String
    Dim cur_dz As String
    Dim next_dz As Double
    Dim cur_shift As String

    Dim PartDest As Part
    Dim InsFactory As InstanceFactory
    Dim MyInstance 'As HybridShapeInstance
    Set PartDest = PartDocumentDest.Part
    Set CreatePolyhedra = PartDest.Bodies.Add
    PartDest.InWorkObject = CreatePolyhedra
    Set InsFactory = PartDest.GetCustomerFactory("InstanceFactory")

    'ReorderList phedraXMLNode

    For i = 1 To phedraXMLNode.childNodes.Length - 1

        cur_dz = str((Val(phedraXMLNode.childNodes.Item(i).Attributes.getNamedItem("z").nodeValue) - _
                    Val(phedraXMLNode.childNodes.Item(i - 1).Attributes.getNamedItem("z").nodeValue)) / 2#)
        cur_rmin1 = phedraXMLNode.childNodes.Item(i - 1).Attributes.getNamedItem("rmin").nodeValue
        cur_rmax1 = phedraXMLNode.childNodes.Item(i - 1).Attributes.getNamedItem("rmax").nodeValue
        cur_rmin2 = phedraXMLNode.childNodes.Item(i).Attributes.getNamedItem("rmin").nodeValue
        cur_rmax2 = phedraXMLNode.childNodes.Item(i).Attributes.getNamedItem("rmax").nodeValue

        If i < phedraXMLNode.childNodes.Length - 1 Then
            next_dz = (Val(phedraXMLNode.childNodes.Item(i + 1).Attributes.getNamedItem("z").nodeValue) - _
                    Val(phedraXMLNode.childNodes.Item(i).Attributes.getNamedItem("z").nodeValue)) / 2#
        End If

        If cur_dz = 0 Then
            GoTo label2
        End If

        CreateHedra path, PartDocumentDest, cur_rmin1, cur_rmax1, cur_rmin2, cur_rmax2, cur_dz, _
                                phedraXMLNode.Attributes.getNamedItem("startphi").nodeValue, _
                                phedraXMLNode.Attributes.getNamedItem("deltaphi").nodeValue, _
                                phedraXMLNode.Attributes.getNamedItem("numsides").nodeValue, "mm", "deg", True


        If i < phedraXMLNode.childNodes.Length - 1 Then
            If next_dz = 0 Then
                cur_shift = str(-(Val(phedraXMLNode.childNodes.Item(i + 2).Attributes.getNamedItem("z").nodeValue) - _
                                Val(phedraXMLNode.childNodes.Item(i - 1).Attributes.getNamedItem("z").nodeValue)) / 2#)
            Else
                cur_shift = str(-(Val(phedraXMLNode.childNodes.Item(i + 1).Attributes.getNamedItem("z").nodeValue) - _
                                Val(phedraXMLNode.childNodes.Item(i - 1).Attributes.getNamedItem("z").nodeValue)) / 2#)
            End If
        Else
            cur_shift = str((Val(phedraXMLNode.childNodes.Item(i - 1).Attributes.getNamedItem("z").nodeValue) - _
                            Val(phedraXMLNode.childNodes.Item(0).Attributes.getNamedItem("z").nodeValue)) / 2#)
        End If
        CreateShift PartDocumentDest, "0", "0", cur_shift, "mm"

label2:
    Next i

End Function

Public Function CreateSphere(path As String, _
                        PartDocumentDest As PartDocument, _
                        pRmin As String, _
                        pRmax As String, _
                        pSPhi As String, _
                        pDPhi As String, _
                        pSTheta As String, _
                        pDTheta As String, _
                        lunit As String, _
                        aunit As String) As Body

    Dim PartDest As Part
    Dim InsFactory As InstanceFactory
    Dim MyInstance 'As HybridShapeInstance
    Set PartDest = PartDocumentDest.Part
    Set CreateSphere = PartDest.Bodies.Add
    PartDest.InWorkObject = CreateSphere
    Set InsFactory = PartDest.GetCustomerFactory("InstanceFactory")

    Dim ZXPlane As Object
    Dim param1 As Parameter
    Dim param2 As Parameter
    Dim param3 As Parameter
    Dim param4 As Parameter
    Dim param5 As Parameter
    Dim param6 As Parameter

    Call InsFactory.BeginInstanceFactory("G4Sphere", (path & "\G4Sphere.CATPart"))
    InsFactory.BeginInstantiate
    Set ZXPlane = PartDest.FindObjectByName("zx plane")
    InsFactory.PutInputData "zx plane", ZXPlane

    Set param1 = InsFactory.GetParameter("pRmin")
    Set param2 = InsFactory.GetParameter("pRmax")
    Set param3 = InsFactory.GetParameter("pSPhi")
    Set param4 = InsFactory.GetParameter("pDPhi")
    Set param5 = InsFactory.GetParameter("pSTheta")
    Set param6 = InsFactory.GetParameter("pDTheta")

    param1.ValuateFromString (str(Val(Trim(pRmin)) * unitConvert(lunit)) & "mm")
    param2.ValuateFromString (str(Val(Trim(pRmax)) * unitConvert(lunit)) & "mm")
    param3.ValuateFromString (str(Val(Trim(pSPhi)) * unitConvert(aunit)) & "deg")
    param4.ValuateFromString (str(Val(Trim(pDPhi)) * unitConvert(aunit)) & "deg")
    param5.ValuateFromString (str(Val(Trim(pSTheta)) * unitConvert(aunit)) & "deg")
    param6.ValuateFromString (str(Val(Trim(pDTheta)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmin, param1, rels, "_pRmin"
    CreateFormula PartDest, pRmax, param2, rels, "_pRmax"
    CreateFormula PartDest, pSPhi, param3, rels, "_pSPhi"
    CreateFormula PartDest, pDPhi, param4, rels, "_pDPhi"
    CreateFormula PartDest, pSTheta, param5, rels, "_pSTheta"
    CreateFormula PartDest, pDTheta, param6, rels, "_pDTheta"

    Set MyInstance = InsFactory.Instantiate
    InsFactory.EndInstantiate
    InsFactory.EndInstanceFactory

End Function

Public Function CreateTorus(path As String, _
                        PartDocumentDest As PartDocument, _
                        pRmin As String, _
                        pRmax As String, _
                        pRtor As String, _
                        pSPhi As String, _
                        pDPhi As String, _
                        lunit As String, _
                        aunit As String) As Body

    Dim PartDest As Part
    Dim InsFactory As InstanceFactory
    Dim MyInstance 'As HybridShapeInstance
    Set PartDest = PartDocumentDest.Part
    Set CreateTorus = PartDest.Bodies.Add
    PartDest.InWorkObject = CreateTorus
    Set InsFactory = PartDest.GetCustomerFactory("InstanceFactory")

    Dim ZXPlane As Object
    Dim param1 As Parameter
    Dim param2 As Parameter
    Dim param3 As Parameter
    Dim param4 As Parameter
    Dim param5 As Parameter

    Call InsFactory.BeginInstanceFactory("G4Torus", (path & "\G4Torus.CATPart"))
    InsFactory.BeginInstantiate
    Set ZXPlane = PartDest.FindObjectByName("zx plane")
    InsFactory.PutInputData "zx plane", ZXPlane

    Set param1 = InsFactory.GetParameter("pRmin")
    Set param2 = InsFactory.GetParameter("pRmax")
    Set param3 = InsFactory.GetParameter("pRtor")
    Set param4 = InsFactory.GetParameter("pSPhi")
    Set param5 = InsFactory.GetParameter("pDPhi")

    param1.ValuateFromString (str(Val(Trim(pRmin)) * unitConvert(lunit)) & "mm")
    param2.ValuateFromString (str(Val(Trim(pRmax)) * unitConvert(lunit)) & "mm")
    param3.ValuateFromString (str(Val(Trim(pRtor)) * unitConvert(lunit)) & "mm")
    param4.ValuateFromString (str(Val(Trim(pSPhi)) * unitConvert(aunit)) & "deg")
    param5.ValuateFromString (str(Val(Trim(pDPhi)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmin, param1, rels, "_pRmin"
    CreateFormula PartDest, pRmax, param2, rels, "_pRmax"
    CreateFormula PartDest, pRtor, param3, rels, "_pRtor"
    CreateFormula PartDest, pSPhi, param4, rels, "_pSPhi"
    CreateFormula PartDest, pDPhi, param5, rels, "_pDPhi"

    Set MyInstance = InsFactory.Instantiate
    InsFactory.EndInstantiate
    InsFactory.EndInstanceFactory

End Function

Public Function CreateTrap(path As String, _
                    PartDocumentDest As PartDocument, _
                    pDz As String, _
                    pTheta As String, _
                    pPhi As String, _
                    pDy1 As String, _
                    pDx1 As String, _
                    pDx2 As String, _
                    pAlp1 As String, _
                    pDy2 As String, _
                    pDx3 As String, _
                    pDx4 As String, _
                    lunit As String, _
                    aunit As String) As Body

    Dim PartDest As Part
    Dim InsFactory As InstanceFactory
    Dim MyInstance 'As HybridShapeInstance
    Set PartDest = PartDocumentDest.Part
    Set CreateTrap = PartDest.Bodies.Add
    PartDest.InWorkObject = CreateTrap
    Set InsFactory = PartDest.GetCustomerFactory("InstanceFactory")

    Dim ZXPlane As Object
    Dim XYPlane As Object
    Dim param1 As Parameter
    Dim param2 As Parameter
    Dim param3 As Parameter
    Dim param4 As Parameter
    Dim param5 As Parameter
    Dim param6 As Parameter
    Dim param7 As Parameter
    Dim param8 As Parameter
    Dim param9 As Parameter
    Dim param10 As Parameter

    Call InsFactory.BeginInstanceFactory("G4Trap", (path & "\G4Trap.CATPart"))
    InsFactory.BeginInstantiate
    Set ZXPlane = PartDest.FindObjectByName("zx plane")
    Set XYPlane = PartDest.FindObjectByName("xy plane")
    InsFactory.PutInputData "zx plane", ZXPlane
    InsFactory.PutInputData "xy plane", XYPlane

    Set param1 = InsFactory.GetParameter("pDz")
    Set param2 = InsFactory.GetParameter("pTheta")
    Set param3 = InsFactory.GetParameter("pPhi")
    Set param4 = InsFactory.GetParameter("pDy1")
    Set param5 = InsFactory.GetParameter("pDx1")

    Set param6 = InsFactory.GetParameter("pDx2")
    Set param7 = InsFactory.GetParameter("pAlp1")
    Set param8 = InsFactory.GetParameter("pDy2")
    Set param9 = InsFactory.GetParameter("pDx3")
    Set param10 = InsFactory.GetParameter("pDx4")

    If (Right(pDz, 3) = ")*2" And Left(pDz, 1) = "(") Then
        pDz = Mid(pDz, 2, Len(pDz) - 4)
        param1.ValuateFromString (str(Val(Trim(pDz)) * unitConvert(lunit)) & "mm")
    Else
        param1.ValuateFromString (str(Val(Trim(pDz)) * unitConvert(lunit) / 2#) & "mm")
    End If
    If (Right(pDy1, 3) = ")*2" And Left(pDy1, 1) = "(") Then
        pDy1 = Mid(pDy1, 2, Len(pDy1) - 4)
        param4.ValuateFromString (str(Val(Trim(pDy1)) * unitConvert(lunit)) & "mm")
    Else
        param4.ValuateFromString (str(Val(Trim(pDy1)) * unitConvert(lunit) / 2#) & "mm")
    End If
    If (Right(pDx1, 3) = ")*2" And Left(pDx1, 1) = "(") Then
        pDx1 = Mid(pDx1, 2, Len(pDx1) - 4)
         param5.ValuateFromString (str(Val(Trim(pDx1)) * unitConvert(lunit)) & "mm")
    Else
         param5.ValuateFromString (str(Val(Trim(pDx1)) * unitConvert(lunit) / 2#) & "mm")
    End If
    If (Right(pDx2, 3) = ")*2" And Left(pDx2, 1) = "(") Then
        pDx2 = Mid(pDx2, 2, Len(pDx2) - 4)
        param6.ValuateFromString (str(Val(Trim(pDx2)) * unitConvert(lunit)) & "mm")
    Else
        param6.ValuateFromString (str(Val(Trim(pDx2)) * unitConvert(lunit) / 2#) & "mm")
    End If
    If (Right(pDy2, 3) = ")*2" And Left(pDy2, 1) = "(") Then
        pDy2 = Mid(pDy2, 2, Len(pDy2) - 4)
        param8.ValuateFromString (str(Val(Trim(pDy2)) * unitConvert(lunit)) & "mm")
    Else
        param8.ValuateFromString (str(Val(Trim(pDy2)) * unitConvert(lunit) / 2#) & "mm")
    End If
    If (Right(pDx3, 3) = ")*2" And Left(pDx3, 1) = "(") Then
        pDx3 = Mid(pDx3, 2, Len(pDx3) - 4)
        param9.ValuateFromString (str(Val(Trim(pDx3)) * unitConvert(lunit)) & "mm")
    Else
        param9.ValuateFromString (str(Val(Trim(pDx3)) * unitConvert(lunit) / 2#) & "mm")
    End If
    If (Right(pDx4, 3) = ")*2" And Left(pDx4, 1) = "(") Then
        pDx4 = Mid(pDx4, 2, Len(pDx4) - 4)
        param10.ValuateFromString (str(Val(Trim(pDx4)) * unitConvert(lunit)) & "mm")
    Else
        param10.ValuateFromString (str(Val(Trim(pDx4)) * unitConvert(lunit) / 2#) & "mm")
    End If

    param3.ValuateFromString (str(Val(Trim(pPhi)) * unitConvert(aunit)) & "deg")
    param7.ValuateFromString (str(Val(Trim(pAlp1)) * unitConvert(aunit)) & "deg")
    param2.ValuateFromString (str(Val(Trim(pTheta)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pDz, param1, rels, "_pDz"
    CreateFormula PartDest, pTheta, param2, rels, "_pTheta"
    CreateFormula PartDest, pPhi, param3, rels, "_pPhi"
    CreateFormula PartDest, pDy1, param4, rels, "_pDy1"
    CreateFormula PartDest, pDx1, param5, rels, "_pDx1"
    CreateFormula PartDest, pDx2, param6, rels, "_pDx2"
    CreateFormula PartDest, pAlp1, param7, rels, "_pAlp1"
    CreateFormula PartDest, pDy2, param8, rels, "_pDy2"
    CreateFormula PartDest, pDx3, param9, rels, "_pDx3"
    CreateFormula PartDest, pDx4, param10, rels, "_pDx4"

    Set MyInstance = InsFactory.Instantiate
    InsFactory.EndInstantiate
    InsFactory.EndInstanceFactory

End Function

Public Function CreateTrd(path As String, _
                    PartDocumentDest As PartDocument, _
                    dx1 As String, _
                    dx2 As String, _
                    dy1 As String, _
                    dy2 As String, _
                    dz As String, _
                    lunit As String) As Body

    Dim PartDest As Part
    Dim InsFactory As InstanceFactory
    Dim MyInstance 'As HybridShapeInstance
    Set PartDest = PartDocumentDest.Part
    Set CreateTrd = PartDest.Bodies.Add
    PartDest.InWorkObject = CreateTrd
    Set InsFactory = PartDest.GetCustomerFactory("InstanceFactory")

    Dim XYPlane As Object
    Dim param1 As Parameter
    Dim param2 As Parameter
    Dim param3 As Parameter
    Dim param4 As Parameter
    Dim param5 As Parameter

    Call InsFactory.BeginInstanceFactory("G4Trd", (path & "\G4Trd.CATPart"))
    InsFactory.BeginInstantiate
    Set XYPlane = PartDest.FindObjectByName("xy plane")
    InsFactory.PutInputData "xy plane", XYPlane

    Set param1 = InsFactory.GetParameter("dx1")
    Set param2 = InsFactory.GetParameter("dx2")
    Set param3 = InsFactory.GetParameter("dy1")
    Set param4 = InsFactory.GetParameter("dy2")
    Set param5 = InsFactory.GetParameter("dz")

    If (Right(dx1, 3) = ")*2" And Left(dx1, 1) = "(") Then
        dx1 = Mid(dx1, 2, Len(dx1) - 4)
        param1.ValuateFromString (str(Val(Trim(dx1)) * unitConvert(lunit)) & "mm")
    Else
        param1.ValuateFromString (str(Val(Trim(dx1)) * unitConvert(lunit) / 2#) & "mm")
    End If
    If (Right(dx2, 3) = ")*2" And Left(dx2, 1) = "(") Then
        dx2 = Mid(dx2, 2, Len(dx2) - 4)
         param2.ValuateFromString (str(Val(Trim(dx2)) * unitConvert(lunit)) & "mm")
    Else
         param2.ValuateFromString (str(Val(Trim(dx2)) * unitConvert(lunit) / 2#) & "mm")
    End If
    If (Right(dy1, 3) = ")*2" And Left(dy1, 1) = "(") Then
        dy1 = Mid(dy1, 2, Len(dy1) - 4)
        param3.ValuateFromString (str(Val(Trim(dy1)) * unitConvert(lunit)) & "mm")
    Else
        param3.ValuateFromString (str(Val(Trim(dy1)) * unitConvert(lunit) / 2#) & "mm")
    End If
    If (Right(dy2, 3) = ")*2" And Left(dy2, 1) = "(") Then
        dy2 = Mid(dy2, 2, Len(dy2) - 4)
        param4.ValuateFromString (str(Val(Trim(dy2)) * unitConvert(lunit)) & "mm")
    Else
        param4.ValuateFromString (str(Val(Trim(dy2)) * unitConvert(lunit) / 2#) & "mm")
    End If
    If (Right(dz, 3) = ")*2" And Left(dz, 1) = "(") Then
        dz = Mid(dz, 2, Len(dz) - 4)
        param5.ValuateFromString (str(Val(Trim(dz)) * unitConvert(lunit)) & "mm")
    Else
        param5.ValuateFromString (str(Val(Trim(dz)) * unitConvert(lunit) / 2#) & "mm")
    End If

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, dx1, param1, rels, "_dx1"
    CreateFormula PartDest, dx2, param2, rels, "_dx2"
    CreateFormula PartDest, dy1, param3, rels, "_dy1"
    CreateFormula PartDest, dy2, param4, rels, "_dy2"
    CreateFormula PartDest, dz, param5, rels, "_Dz"

    Set MyInstance = InsFactory.Instantiate
    InsFactory.EndInstantiate
    InsFactory.EndInstanceFactory

End Function

Public Function CreateTubs(path As String, _
                    PartDocumentDest As PartDocument, _
                    pRmin As String, _
                    pRmax As String, _
                    pDz As String, _
                    pSPhi As String, _
                    pDPhi As String, _
                    lunit As String, _
                    aunit As String) As Body

    Dim PartDest As Part
    Dim InsFactory As InstanceFactory
    Dim MyInstance 'As HybridShapeInstance
    Set PartDest = PartDocumentDest.Part
    Set CreateTubs = PartDest.Bodies.Add
    PartDest.InWorkObject = CreateTubs
    Set InsFactory = PartDest.GetCustomerFactory("InstanceFactory")

    Dim ZXPlane As Object
    Dim param1 As Parameter
    Dim param2 As Parameter
    Dim param3 As Parameter
    Dim param4 As Parameter
    Dim param5 As Parameter

    Call InsFactory.BeginInstanceFactory("G4Tubs", (path & "\G4Tubs.CATPart"))
    InsFactory.BeginInstantiate
    Set ZXPlane = PartDest.FindObjectByName("zx plane")
    InsFactory.PutInputData "zx plane", ZXPlane

    Set param1 = InsFactory.GetParameter("pRMin")
    Set param2 = InsFactory.GetParameter("pRMax")
    Set param3 = InsFactory.GetParameter("pDz")
    Set param4 = InsFactory.GetParameter("pSPhi")
    Set param5 = InsFactory.GetParameter("pDPhi")

    If (Right(pDz, 3) = ")*2" And Left(pDz, 1) = "(") Then
        pDz = Mid(pDz, 2, Len(pDz) - 4)
        param3.ValuateFromString (str(Val(Trim(pDz)) * unitConvert(lunit)) & "mm")
    Else
        param3.ValuateFromString (str(Val(Trim(pDz)) * unitConvert(lunit) / 2#) & "mm")
    End If

    param1.ValuateFromString (str(Val(Trim(pRmin)) * unitConvert(lunit)) & "mm")
    param2.ValuateFromString (str(Val(Trim(pRmax)) * unitConvert(lunit)) & "mm")
    param4.ValuateFromString (str(Val(Trim(pSPhi)) * unitConvert(aunit)) & "deg")
    param5.ValuateFromString (str(Val(Trim(pDPhi)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pRmin, param1, rels, "_pRmin"
    CreateFormula PartDest, pRmax, param2, rels, "_pRmax"
    CreateFormula PartDest, pDz, param3, rels, "_pDz"
    CreateFormula PartDest, pSPhi, param4, rels, "_pSPhi"
    CreateFormula PartDest, pDPhi, param5, rels, "_pDPhi"

    Set MyInstance = InsFactory.Instantiate
    InsFactory.EndInstantiate
    InsFactory.EndInstanceFactory

End Function

Public Function CreateTwistedBox(path As String, _
                    PartDocumentDest As PartDocument, _
                    twistedangle As String, _
                    pDx As String, _
                    pDy As String, _
                    pDz As String, _
                    lunit As String, _
                    aunit As String) As Body

    Dim PartDest As Part
    Dim InsFactory As InstanceFactory
    Dim MyInstance 'As HybridShapeInstance
    Set PartDest = PartDocumentDest.Part
    Set CreateTwistedBox = PartDest.Bodies.Add
    PartDest.InWorkObject = CreateTwistedBox
    Set InsFactory = PartDest.GetCustomerFactory("InstanceFactory")

    Dim XYPlane As Object
    Dim param1 As Parameter
    Dim param2 As Parameter
    Dim param3 As Parameter
    Dim param4 As Parameter

    Call InsFactory.BeginInstanceFactory("G4TwistedBox", (path & "\G4TwistedBox.CATPart"))
    InsFactory.BeginInstantiate
    Set XYPlane = PartDest.FindObjectByName("xy plane")
    InsFactory.PutInputData "xy plane", XYPlane

    Set param1 = InsFactory.GetParameter("twistedangle")
    Set param2 = InsFactory.GetParameter("pDx")
    Set param3 = InsFactory.GetParameter("pDy")
    Set param4 = InsFactory.GetParameter("pDz")

    If (Right(pDx, 3) = ")*2" And Left(pDx, 1) = "(") Then
        pDx = Mid(pDx, 2, Len(pDx) - 4)
    End If
    If (Right(pDy, 3) = ")*2" And Left(pDy, 1) = "(") Then
        pDy = Mid(pDy, 2, Len(pDy) - 4)
    End If
    If (Right(pDz, 3) = ")*2" And Left(pDz, 1) = "(") Then
        pDz = Mid(pDz, 2, Len(pDz) - 4)
    End If

    param1.ValuateFromString (str(Val(Trim(twistedangle)) * unitConvert(aunit)) & "deg")
    param2.ValuateFromString (str(Val(Trim(pDx)) * unitConvert(lunit)) & "mm")
    param3.ValuateFromString (str(Val(Trim(pDy)) * unitConvert(lunit)) & "mm")
    param4.ValuateFromString (str(Val(Trim(pDz)) * unitConvert(lunit)) & "mm")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, twistedangle, param1, rels, "_twistedangle"
    CreateFormula PartDest, pDx, param2, rels, "_pDx"
    CreateFormula PartDest, pDy, param3, rels, "_pDy"
    CreateFormula PartDest, pDz, param4, rels, "_pDz"

    Set MyInstance = InsFactory.Instantiate
    InsFactory.EndInstantiate
    InsFactory.EndInstanceFactory

End Function

Public Function CreateTwistedTrap(path As String, _
                    PartDocumentDest As PartDocument, _
                    twistedangle As String, _
                    pDz As String, _
                    pTheta As String, _
                    pPhi As String, _
                    pDy1 As String, _
                    pDx1 As String, _
                    pDx2 As String, _
                    pDy2 As String, _
                    pDx3 As String, _
                    pDx4 As String, _
                    pAlph As String, _
                    lunit As String, _
                    aunit As String) As Body

    Dim PartDest As Part
    Dim InsFactory As InstanceFactory
    Dim MyInstance 'As HybridShapeInstance
    Set PartDest = PartDocumentDest.Part
    Set CreateTwistedTrap = PartDest.Bodies.Add
    PartDest.InWorkObject = CreateTwistedTrap
    Set InsFactory = PartDest.GetCustomerFactory("InstanceFactory")

    Dim ZXPlane As Object
    Dim XYPlane As Object
    Dim param1 As Parameter
    Dim param2 As Parameter
    Dim param3 As Parameter
    Dim param4 As Parameter
    Dim param5 As Parameter
    Dim param6 As Parameter
    Dim param7 As Parameter
    Dim param8 As Parameter
    Dim param9 As Parameter
    Dim param10 As Parameter
    Dim param11 As Parameter

    Call InsFactory.BeginInstanceFactory("G4TwistedTrap", (path & "\G4TwistedTrap.CATPart"))
    InsFactory.BeginInstantiate
    Set ZXPlane = PartDest.FindObjectByName("zx plane")
    Set XYPlane = PartDest.FindObjectByName("xy plane")
    InsFactory.PutInputData "zx plane", ZXPlane
    InsFactory.PutInputData "xy plane", XYPlane

    Set param1 = InsFactory.GetParameter("twistedangle")
    Set param2 = InsFactory.GetParameter("pDz")
    Set param3 = InsFactory.GetParameter("pTheta")
    Set param4 = InsFactory.GetParameter("pPhi")
    Set param5 = InsFactory.GetParameter("pDy1")
    Set param6 = InsFactory.GetParameter("pDx1")
    Set param7 = InsFactory.GetParameter("pDx2")
    Set param8 = InsFactory.GetParameter("pDy2")
    Set param9 = InsFactory.GetParameter("pDx3")
    Set param10 = InsFactory.GetParameter("pDx4")
    Set param11 = InsFactory.GetParameter("pAlph")

    If (Right(pDz, 3) = ")*2" And Left(pDz, 1) = "(") Then
        pDz = Mid(pDz, 2, Len(pDz) - 4)
    End If
    If (Right(pDy1, 3) = ")*2" And Left(pDy1, 1) = "(") Then
        pDy1 = Mid(pDy1, 2, Len(pDy1) - 4)
    End If
    If (Right(pDx1, 3) = ")*2" And Left(pDx1, 1) = "(") Then
        pDx1 = Mid(pDx1, 2, Len(pDx1) - 4)
    End If
    If (Right(pDx2, 3) = ")*2" And Left(pDx2, 1) = "(") Then
        pDx2 = Mid(pDx2, 2, Len(pDx2) - 4)
    End If
    If (Right(pDy2, 3) = ")*2" And Left(pDy2, 1) = "(") Then
        pDy2 = Mid(pDy2, 2, Len(pDy2) - 4)
    End If
    If (Right(pDx3, 3) = ")*2" And Left(pDx3, 1) = "(") Then
        pDx3 = Mid(pDx3, 2, Len(pDx3) - 4)
    End If
    If (Right(pDx4, 3) = ")*2" And Left(pDx4, 1) = "(") Then
        pDx4 = Mid(pDx4, 2, Len(pDx4) - 4)
    End If

    param1.ValuateFromString (str(Val(Trim(twistedangle)) * unitConvert(aunit)) & "deg")
    param2.ValuateFromString (str(Val(Trim(pDz)) * unitConvert(lunit)) & "mm")
    param3.ValuateFromString (str(Val(Trim(pTheta)) * unitConvert(aunit)) & "deg")
    param4.ValuateFromString (str(Val(Trim(pPhi)) * unitConvert(aunit)) & "deg")
    param5.ValuateFromString (str(Val(Trim(pDy1)) * unitConvert(lunit)) & "mm")
    param6.ValuateFromString (str(Val(Trim(pDx1)) * unitConvert(lunit)) & "mm")
    param7.ValuateFromString (str(Val(Trim(pDx2)) * unitConvert(lunit)) & "mm")
    param8.ValuateFromString (str(Val(Trim(pDy2)) * unitConvert(lunit)) & "mm")
    param9.ValuateFromString (str(Val(Trim(pDx3)) * unitConvert(lunit)) & "mm")
    param10.ValuateFromString (str(Val(Trim(pDx4)) * unitConvert(lunit)) & "mm")
    param11.ValuateFromString (str(Val(Trim(pAlph)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, twistedangle, param1, rels, "_twistedangle"
    CreateFormula PartDest, pDz, param2, rels, "_pDz"
    CreateFormula PartDest, pTheta, param3, rels, "_pTheta"
    CreateFormula PartDest, pPhi, param4, rels, "_pPhi"
    CreateFormula PartDest, pDy1, param5, rels, "_pDy1"
    CreateFormula PartDest, pDx1, param6, rels, "_pDx1"
    CreateFormula PartDest, pDx2, param7, rels, "_pDx2"
    CreateFormula PartDest, pDy2, param8, rels, "_pDy2"
    CreateFormula PartDest, pDx3, param9, rels, "_pDx3"
    CreateFormula PartDest, pDx4, param10, rels, "_pDx4"
    CreateFormula PartDest, pAlph, param11, rels, "_pAlph"

    Set MyInstance = InsFactory.Instantiate
    InsFactory.EndInstantiate
    InsFactory.EndInstanceFactory

End Function

Public Function CreateTwistedTrd(path As String, _
                    PartDocumentDest As PartDocument, _
                    pDx1 As String, _
                    pDx2 As String, _
                    pDy1 As String, _
                    pDy2 As String, _
                    pDz As String, _
                    twistedangle As String, _
                    lunit As String, _
                    aunit As String) As Body

    Dim PartDest As Part
    Dim InsFactory As InstanceFactory
    Dim MyInstance 'As HybridShapeInstance
    Set PartDest = PartDocumentDest.Part
    Set CreateTwistedTrd = PartDest.Bodies.Add
    PartDest.InWorkObject = CreateTwistedTrd
    Set InsFactory = PartDest.GetCustomerFactory("InstanceFactory")

    Dim XYPlane As Object
    Dim param1 As Parameter
    Dim param2 As Parameter
    Dim param3 As Parameter
    Dim param4 As Parameter
    Dim param5 As Parameter
    Dim param6 As Parameter

    Call InsFactory.BeginInstanceFactory("G4TwistedTrd", (path & "\G4TwistedTrd.CATPart"))
    InsFactory.BeginInstantiate
    Set XYPlane = PartDest.FindObjectByName("xy plane")
    InsFactory.PutInputData "xy plane", XYPlane

    Set param1 = InsFactory.GetParameter("pDx1")
    Set param2 = InsFactory.GetParameter("pDx2")
    Set param3 = InsFactory.GetParameter("pDy1")
    Set param4 = InsFactory.GetParameter("pDy2")
    Set param5 = InsFactory.GetParameter("pDz")
    Set param6 = InsFactory.GetParameter("twistedangle")

    If (Right(pDx1, 3) = ")*2" And Left(pDx1, 1) = "(") Then
        pDx1 = Mid(pDx1, 2, Len(pDx1) - 4)
    End If
    If (Right(pDx2, 3) = ")*2" And Left(pDx2, 1) = "(") Then
        pDx2 = Mid(pDx2, 2, Len(pDx2) - 4)
    End If
    If (Right(pDy1, 3) = ")*2" And Left(pDy1, 1) = "(") Then
        pDy1 = Mid(pDy1, 2, Len(pDy1) - 4)
    End If
    If (Right(pDy2, 3) = ")*2" And Left(pDy2, 1) = "(") Then
        pDy2 = Mid(pDy2, 2, Len(pDy2) - 4)
    End If
    If (Right(pDz, 3) = ")*2" And Left(pDz, 1) = ")") Then
        pDz = Mid(pDz, 2, Len(pDz) - 4)
    End If

    param1.ValuateFromString (str(Val(Trim(pDx1)) * unitConvert(lunit)) & "mm")
    param2.ValuateFromString (str(Val(Trim(pDx2)) * unitConvert(lunit)) & "mm")
    param3.ValuateFromString (str(Val(Trim(pDy1)) * unitConvert(lunit)) & "mm")
    param4.ValuateFromString (str(Val(Trim(pDy2)) * unitConvert(lunit)) & "mm")
    param5.ValuateFromString (str(Val(Trim(pDz)) * unitConvert(lunit)) & "mm")
    param6.ValuateFromString (str(Val(Trim(twistedangle)) * unitConvert(aunit)) & "deg")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, pDx1, param1, rels, "_pDx1"
    CreateFormula PartDest, pDx2, param2, rels, "_pDx2"
    CreateFormula PartDest, pDy1, param3, rels, "_pDy1"
    CreateFormula PartDest, pDy2, param4, rels, "_pDy2"
    CreateFormula PartDest, pDz, param5, rels, "_pDz"
    CreateFormula PartDest, twistedangle, param6, rels, "_twistedangle"

    Set MyInstance = InsFactory.Instantiate
    InsFactory.EndInstantiate
    InsFactory.EndInstanceFactory

End Function

Public Function CreateTwistedTubs(path As String, _
                    PartDocumentDest As PartDocument, _
                    twistedangle As String, _
                    endinnerrad As String, _
                    endouterrad As String, _
                    halfzlen As String, _
                    dphi As String, _
                    lunit As String, _
                    aunit As String) As Body

    Dim PartDest As Part
    Dim InsFactory As InstanceFactory
    Dim MyInstance 'As HybridShapeInstance
    Set PartDest = PartDocumentDest.Part
    Set CreateTwistedTubs = PartDest.Bodies.Add
    PartDest.InWorkObject = CreateTwistedTubs
    Set InsFactory = PartDest.GetCustomerFactory("InstanceFactory")

    Dim XYPlane As Object
    Dim param1 As Parameter
    Dim param2 As Parameter
    Dim param3 As Parameter
    Dim param4 As Parameter
    Dim param5 As Parameter

    Call InsFactory.BeginInstanceFactory("G4TwistedTubs", (path & "\G4TwistedTubs.CATPart"))
    InsFactory.BeginInstantiate
    Set XYPlane = PartDest.FindObjectByName("xy plane")
    InsFactory.PutInputData "xy plane", XYPlane

    Set param1 = InsFactory.GetParameter("twistedangle")
    Set param2 = InsFactory.GetParameter("endinnerrad")
    Set param3 = InsFactory.GetParameter("endouterrad")
    Set param4 = InsFactory.GetParameter("halfzlen")
    Set param5 = InsFactory.GetParameter("dphi")

    If (Right(halfzlen, 3) = ")*2" And Left(halfzlen, 1) = "(") Then
        halfzlen = Mid(halfzlen, 2, Len(halfzlen) - 4)
    End If

    param1.ValuateFromString (str(Val(Trim(twistedangle)) * unitConvert(aunit)) & "deg")
    param2.ValuateFromString (str(Val(Trim(endinnerrad)) * unitConvert(lunit)) & "mm")
    param3.ValuateFromString (str(Val(Trim(endouterrad)) * unitConvert(lunit)) & "mm")
    param4.ValuateFromString (str(Val(Trim(halfzlen)) * unitConvert(lunit)) & "mm")
    param5.ValuateFromString (str(Val(Trim(dphi)) * unitConvert(lunit)) & "mm")

    Dim i As Integer
    Dim flag As Integer
    Dim char As String
    Dim prodDoc As ProductDocument
    Set prodDoc = CATIA.ActiveDocument
    Dim prod As Product
    Set prod = prodDoc.Product
    Dim rels As Relations
    Set rels = prod.Relations
    Dim form As Formula

    ' Parameterization
    CreateFormula PartDest, twistedangle, param1, rels, "_twistedangle"
    CreateFormula PartDest, endinnerrad, param2, rels, "_endinnerrad"
    CreateFormula PartDest, endouterrad, param3, rels, "_endouterrad"
    CreateFormula PartDest, halfzlen, param4, rels, "_halfzlen"
    CreateFormula PartDest, dphi, param5, rels, "_dphi"

    Set MyInstance = InsFactory.Instantiate
    InsFactory.EndInstantiate
    InsFactory.EndInstanceFactory

End Function

Public Function CreateXtru(path As String, _
                           PartDocumentDest As PartDocument, _
                           lunit As String, _
                           xtruXMLNode As IXMLDOMNode) As Body

    Dim PartDest As Part
    Dim originElements1 As OriginElements
    Dim refXYPlane As Reference

    Set PartDest = PartDocumentDest.Part
    Set originElements1 = PartDest.OriginElements
    Set refXYPlane = originElements1.PlaneXY

    ' Create a geometrical set and a sketch for the xtru blueprint
    Dim hBodies1 As HybridBodies
    Dim hBody1 As HybridBody
    Dim hSketches1 As Sketches
    Dim sketch1 As Sketch

    Set hBodies1 = PartDest.HybridBodies
    Set hBody1 = hBodies1.Add()
    hBody1.name = "Geometrical Set.1"
    Set hSketches1 = hBody1.HybridSketches
    Set sketch1 = hSketches1.Add(refXYPlane)

    ' Draw the sketch =============================================================================
    PartDest.InWorkObject = sketch1
    
    Dim factory2D1 As Factory2D
    Set factory2D1 = sketch1.OpenEdition()

    Dim repNameVal As Integer
    repNameVal = 3 ' Start from 3 as 1 and 2 are reserved for default sketch objects (HDirection and VDirection)

    Dim firstPoint ' As Point2D
    Dim lastPoint ' As Point2D
    Dim curLine As line2D
    Dim p0(0 To 1)
    Dim p1(0 To 1)

    ' Loop over twoDimVertex tags
    Dim i As Integer
    For i = 0 To xtruXMLNode.childNodes.Length - 1
        If (xtruXMLNode.childNodes.Item(i).baseName = "twoDimVertex") Then
            Dim curX As Double
            Dim curY As Double
            curX = xtruXMLNode.childNodes.Item(i).Attributes.getNamedItem("x").nodeValue
            curY = xtruXMLNode.childNodes.Item(i).Attributes.getNamedItem("y").nodeValue

            ' Create a point in the sketch
            Dim curPoint ' As Point2D
            Set curPoint = factory2D1.CreatePoint(curX, curY)
        
            curPoint.ReportName = str(repNameVal)
            repNameVal = repNameVal + 1

            ' Store the first point
            If (i = 0) Then
                Set firstPoint = curPoint
            End If

            ' For each point starting from the second
            ' connect it to the previous point with a new line
            If (i > 0) Then
                lastPoint.GetCoordinates p0
                curPoint.GetCoordinates p1
    
                Set curLine = factory2D1.CreateLine(p0(0), p0(1), p1(0), p1(1))
                curLine.ReportName = str(repNameVal)
                repNameVal = repNameVal + 1
                curLine.StartPoint = lastPoint
                curLine.EndPoint = curPoint
            End If
    
            Set lastPoint = curPoint

        End If ' if twoDimVertex
    Next i

    ' Create the last line connecting the last and the first points
    lastPoint.GetCoordinates p0
    firstPoint.GetCoordinates p1
    Set curLine = factory2D1.CreateLine(p0(0), p0(1), p1(0), p1(1))
    curLine.ReportName = str(repNameVal)
    repNameVal = repNameVal + 1
    curLine.StartPoint = lastPoint
    curLine.EndPoint = firstPoint

    ' Finalize sketch creation
    ' Unfortunately update is required for the UDF creation to work
    sketch1.CloseEdition
    PartDest.Update

    ' End of draw the sketch ======================================================================

    ' Parse <section> tags and store z, x, y, scale values in the arrays
    ' For 2 sections case we can ignore zOrder attributes.
    Dim zPos(0 To 1) As Double
    Dim xOff(0 To 1) As Double
    Dim yOff(0 To 1) As Double
    Dim scFac(0 To 1) As Double

    Dim sectionCounter As Integer
    sectionCounter = 0
    For i = 0 To xtruXMLNode.childNodes.Length - 1
        If (xtruXMLNode.childNodes.Item(i).baseName = "section") Then
            zPos(sectionCounter) = xtruXMLNode.childNodes.Item(i).Attributes.getNamedItem("zPosition").nodeValue
            xOff(sectionCounter) = xtruXMLNode.childNodes.Item(i).Attributes.getNamedItem("xOffset").nodeValue
            yOff(sectionCounter) = xtruXMLNode.childNodes.Item(i).Attributes.getNamedItem("yOffset").nodeValue
            scFac(sectionCounter) = xtruXMLNode.childNodes.Item(i).Attributes.getNamedItem("scalingFactor").nodeValue
            sectionCounter = sectionCounter + 1
        End If ' if section
    Next i

    If (sectionCounter <> 2) Then
        'TODO exception
        MsgBox "Xtru tag contains more than 2 sections. Only 2 sections are currently supported. Aborting.", vbCritical
        End
    End If

    ' Create a body
    Set CreateXtru = PartDest.Bodies.Add
    PartDest.InWorkObject = CreateXtru

    ' Create the UDF
    Dim InsFactory As InstanceFactory
    Set InsFactory = PartDest.GetCustomerFactory("InstanceFactory")
    Call InsFactory.BeginInstanceFactory("G4Xtru2sec", (path & "\G4Xtru2sec.CATPart"))
    InsFactory.BeginInstantiate
    InsFactory.PutInputData "Blueprint", sketch1

    Dim param1 As Parameter
    Dim param2 As Parameter
    Dim param3 As Parameter
    Dim param4 As Parameter
    Dim param5 As Parameter
    Dim param6 As Parameter
    Dim param7 As Parameter
    Dim param8 As Parameter

    Set param1 = InsFactory.GetParameter("z_bottom")
    Set param2 = InsFactory.GetParameter("scale_bottom")
    Set param3 = InsFactory.GetParameter("x_bottom")
    Set param4 = InsFactory.GetParameter("y_bottom")
    Set param5 = InsFactory.GetParameter("z_top")
    Set param6 = InsFactory.GetParameter("scale_top")
    Set param7 = InsFactory.GetParameter("x_top")
    Set param8 = InsFactory.GetParameter("y_top")

    param1.ValuateFromString (str(Val(Trim(zPos(0))) * unitConvert(lunit)) & "mm")
    param2.ValuateFromString (str(Val(Trim(scFac(0)))))
    param3.ValuateFromString (str(Val(Trim(xOff(0))) * unitConvert(lunit)) & "mm")
    param4.ValuateFromString (str(Val(Trim(yOff(0))) * unitConvert(lunit)) & "mm")

    param5.ValuateFromString (str(Val(Trim(zPos(1))) * unitConvert(lunit)) & "mm")
    param6.ValuateFromString (str(Val(Trim(scFac(1)))))
    param7.ValuateFromString (str(Val(Trim(xOff(1))) * unitConvert(lunit)) & "mm")
    param8.ValuateFromString (str(Val(Trim(yOff(1))) * unitConvert(lunit)) & "mm")

    'TODO implement parameterization

    ' Finalize UDF creation
    Dim MyInstance 'As HybridShapeInstance
    Set MyInstance = InsFactory.Instantiate
    InsFactory.EndInstantiate
    InsFactory.EndInstanceFactory

End Function

'reorder list so that it will be increasing z
Public Sub ReorderList(pconXMLNode As IXMLDOMNode)

    Dim i As Integer
    Dim j As Integer

    Dim cur_z As Double
    Dim cur_min As Double
    Dim cur_threshold As Double
    Dim cur_min_index As Integer
    Dim cur_min_node As IXMLDOMNode

    For j = 0 To (pconXMLNode.childNodes.Length - 1)
'        MsgBox pconXMLNode.xml
        cur_min = Val(pconXMLNode.childNodes.Item(0).Attributes.getNamedItem("z").nodeValue)
        cur_min_index = 0
        For i = 0 To (pconXMLNode.childNodes.Length - j - 1)
            cur_z = Val(pconXMLNode.childNodes.Item(i).Attributes.getNamedItem("z").nodeValue)
            If (cur_z < cur_min) Then
                If (j = 0) Then
                    cur_min = cur_z
                    cur_min_index = i
                Else
                    If (j > 0) Then
                        cur_min = cur_z
                        cur_min_index = i
                    End If
                End If
            End If
        Next i
        Set cur_min_node = pconXMLNode.childNodes.Item(cur_min_index)
        pconXMLNode.RemoveChild cur_min_node
        pconXMLNode.appendChild cur_min_node
    Next j

End Sub

Public Sub AddTranslation(bd As Body, _
                    PartDocumentDest As PartDocument, _
                    x As String, _
                    y As String, _
                    z As String, _
                    lunit As String)

    Dim shpFactory As ShapeFactory
    Dim trans As Translate
    Dim hybShpTrans As HybridShapeTranslate
    Dim PartDest As Part
    Set PartDest = PartDocumentDest.Part
    PartDest.InWorkObject = bd   '  is it needed here ?

    Set shpFactory = PartDest.ShapeFactory
    'Set trans = shpFactory.AddNewTranslate2(Sqr(x * x + y * y + z * z))
    Set trans = shpFactory.AddNewTranslate2(0)
    Set hybShpTrans = trans.HybridShape
    hybShpTrans.VectorType = 2
    hybShpTrans.CoordXValue = Val(x) * unitConvert(lunit) / 1000#
    hybShpTrans.CoordYValue = Val(y) * unitConvert(lunit) / 1000#
    hybShpTrans.CoordZValue = Val(z) * unitConvert(lunit) / 1000#

    Dim prodDoc As ProductDocument
    Set prodDoc = CATIA.ActiveDocument
    Dim prod As Product
    Set prod = prodDoc.Product
    Dim rels As Relations
    Set rels = prod.Relations
    Dim params As Parameters
    Set params = prod.Parameters
    
    'Dim tNr As Integer
    'tNr = getTransNr(PartDocumentDest.Part)

    ' Parameterization
    CreateFormula PartDocumentDest.Part, z, params.Item(PartDocumentDest.Part.name & "\" & bd.name & "\" & hybShpTrans.name & "\CoordZ"), rels, "_z"
    CreateFormula PartDocumentDest.Part, y, params.Item(PartDocumentDest.Part.name & "\" & bd.name & "\" & hybShpTrans.name & "\CoordY"), rels, "_y"
    CreateFormula PartDocumentDest.Part, x, params.Item(PartDocumentDest.Part.name & "\" & bd.name & "\" & hybShpTrans.name & "\CoordX"), rels, "_x"

End Sub

Public Sub AddRotation(bd As Body, _
                partDoc As PartDocument, _
                axis As String, _
                angle As String, _
                lunit As String)

    Dim hybShpFactory As HybridShapeFactory
    Dim shpFactory As ShapeFactory
    Dim origin As OriginElements
    Dim sel As Selection
    Dim visPropSet As VisPropertySet
    Dim refPlaneXY As Reference
    Dim refPlaneYZ As Reference
    Dim refPlaneZX As Reference

    Set hybShpFactory = partDoc.Part.HybridShapeFactory
    Set shpFactory = partDoc.Part.ShapeFactory
    Set origin = partDoc.Part.OriginElements
    Set sel = CATIA.ActiveDocument.Selection
    Set visPropSet = sel.VisProperties
    Set refPlaneXY = partDoc.Part.CreateReferenceFromObject(origin.PlaneXY)
    Set refPlaneYZ = partDoc.Part.CreateReferenceFromObject(origin.PlaneYZ)
    Set refPlaneZX = partDoc.Part.CreateReferenceFromObject(origin.PlaneZX)

    Dim Intersection_XY_ZX As HybridShapeIntersection
    Dim Intersection_YZ_XY As HybridShapeIntersection
    Dim Intersection_ZX_YZ As HybridShapeIntersection
    Dim hybShpRotX As HybridShapeRotate
    Dim hybShpRotY As HybridShapeRotate
    Dim hybShpRotZ As HybridShapeRotate
    Dim rotX As Rotate
    Dim rotY As Rotate
    Dim rotZ As Rotate
    Dim refAxisX As Reference
    Dim refAxisY As Reference
    Dim refAxisZ As Reference

    partDoc.Part.InWorkObject = bd   '  is it needed here ?

    ' Parameterization
    Dim prodDoc As ProductDocument
    Set prodDoc = CATIA.ActiveDocument
    Dim prod As Product
    Set prod = prodDoc.Product
    Dim rels As Relations
    Set rels = prod.Relations

    Select Case axis
        Case "X", "x"
            Set Intersection_XY_ZX = hybShpFactory.AddNewIntersection(refPlaneXY, refPlaneZX)
            Intersection_XY_ZX.PointType = 0
            bd.InsertHybridShape Intersection_XY_ZX
'            partDoc.Part.InWorkObject = Intersection_XY_ZX
            Intersection_XY_ZX.name = "X axis"
            sel.Clear
            sel.Add Intersection_XY_ZX
            visPropSet.SetShow catVisPropertyNoShowAttr
            sel.Clear
            Set refAxisX = partDoc.Part.CreateReferenceFromObject(Intersection_XY_ZX)
            Set rotX = shpFactory.AddNewRotate2(refAxisX, Val(angle) * unitConvert(lunit))
            Set hybShpRotX = rotX.HybridShape
            hybShpRotX.RotationType = 0
            hybShpRotX.axis = refAxisX
            hybShpRotX.name = "Rotate.X"
'            partDoc.Part.InWorkObject = hybShpRotX
            ' Parameterization
            CreateFormula partDoc.Part, angle, rotX.angle, rels, "_rotX"
        Case "Y", "y"
            Set Intersection_YZ_XY = hybShpFactory.AddNewIntersection(refPlaneYZ, refPlaneXY)
            Intersection_YZ_XY.PointType = 0
            bd.InsertHybridShape Intersection_YZ_XY
'            partDoc.Part.InWorkObject = Intersection_YZ_XY
            Intersection_YZ_XY.name = "Y axis"
            sel.Clear
            sel.Add Intersection_YZ_XY
            visPropSet.SetShow catVisPropertyNoShowAttr
            sel.Clear
            Set refAxisY = partDoc.Part.CreateReferenceFromObject(Intersection_YZ_XY)
            Set rotY = shpFactory.AddNewRotate2(refAxisY, Val(angle) * unitConvert(lunit))
            Set hybShpRotY = rotY.HybridShape
            hybShpRotY.RotationType = 0
            hybShpRotY.axis = refAxisY
            hybShpRotY.name = "Rotate.Y"
'            partDoc.Part.InWorkObject = hybShpRotY
            ' Parameterization
            CreateFormula partDoc.Part, angle, rotY.angle, rels, "_rotY"
        Case "Z", "z"
            Set Intersection_ZX_YZ = hybShpFactory.AddNewIntersection(refPlaneZX, refPlaneYZ)
            Intersection_ZX_YZ.PointType = 0
            bd.InsertHybridShape Intersection_ZX_YZ
'            partDoc.Part.InWorkObject = Intersection_ZX_YZ
            Intersection_ZX_YZ.name = "Z axis"
            sel.Clear
            sel.Add Intersection_ZX_YZ
            visPropSet.SetShow catVisPropertyNoShowAttr
            sel.Clear
            Set refAxisZ = partDoc.Part.CreateReferenceFromObject(Intersection_ZX_YZ)
            Set rotZ = shpFactory.AddNewRotate2(refAxisZ, Val(angle) * unitConvert(lunit))
            Set hybShpRotZ = rotZ.HybridShape
            hybShpRotZ.RotationType = 0
            hybShpRotZ.axis = refAxisZ
            hybShpRotZ.name = "Rotate.Z"
'            partDoc.Part.InWorkObject = hybShpRotZ
            ' Parameterization
            CreateFormula partDoc.Part, angle, rotZ.angle, rels, "_rotZ"
    End Select

End Sub

Public Sub CreateShift(PartDocumentDest As PartDocument, _
                        x As String, y As String, z As String, _
                        lunit As String)

    Dim hybShpFactory As HybridShapeFactory
    Dim shpFactory As ShapeFactory
    Dim hybShpTrans As HybridShapeTranslate
    Dim trans As Translate
    Set hybShpFactory = PartDocumentDest.Part.HybridShapeFactory
    Set shpFactory = PartDocumentDest.Part.ShapeFactory
    'Translation
    Set trans = shpFactory.AddNewTranslate2(0)
    Set hybShpTrans = trans.HybridShape
    hybShpTrans.VectorType = 2
    hybShpTrans.CoordXValue = Val(x) * unitConvert(lunit) / 1000#
    hybShpTrans.CoordYValue = Val(y) * unitConvert(lunit) / 1000#
    hybShpTrans.CoordZValue = Val(z) * unitConvert(lunit) / 1000#
    hybShpTrans.name = "Shift." & Mid(hybShpTrans.name, 11)
    PartDocumentDest.Part.InWorkObject = hybShpTrans   '  is it needed here ?

End Sub

Public Function parseFormula(str As String, parType As String) As String
    str = Replace(str, "*DEGtoRAD", "")
    str = Replace(str, "DEGtoRAD*", "")
    str = Replace(str, "/DEGtoRAD", "")

    Dim objRegExp As RegExp
    Dim objMatch As Match

    Set objRegExp = New RegExp
    objRegExp.Pattern = "([a-z,A-Z,_]+)"
    objRegExp.IgnoreCase = True
    objRegExp.Global = True
    Dim colVarMatches   As MatchCollection

    Dim col As New Collection
    Set col = getTrigBoundaries(str)
    Dim pos As Integer
    Dim str1 As String
    Dim str2 As String
    Dim k As Integer
    k = 0

    Dim dimK As String
    If (parType = "length") Then
        dimK = "*1mm"
    ElseIf (parType = "angle") Then
        dimK = "*1deg"
    Else
        MsgBox "Wrong parameter type"
    End If

    'Простановка размерных коэффециентов в тригонометрических формулах
    Set col = sortCol(col)

    Dim j As Integer
    Dim kfNr As Integer
    kfNr = 0
    For j = 1 To col.Count
        j = j + 1
        str1 = Mid(str, 1, col.Item(j) + kfNr * Len("*1deg") - 1)
        str2 = Mid(str, col.Item(j) + kfNr * Len("*1deg"))
        str = str1 & "*1deg" & str2
        kfNr = kfNr + 1
        'col.Item(j) = col.Item(j) + Len("*1deg")
    Next j
    Set colVarMatches = objRegExp.Execute(str)
    'Простановка размерных коэффициентов после переменных
'    For Each objMatch In colVarMatches
'        If objMatch.Value <> "abs" And objMatch.Value <> "deg" And objMatch.Value <> "atan" Then
'            If inTrig(objMatch.FirstIndex + 4, col) = False Then
'                str1 = Mid(str, 1, objMatch.FirstIndex + objMatch.Length + Len(dimK) * k)
'                str2 = Mid(str, objMatch.FirstIndex + objMatch.Length + Len(dimK) * k + 1)
'                str = str1 & dimK & str2
'                k = k + 1
'            End If
'        End If
'    Next objMatch

    objRegExp.Pattern = "([\(,\+,\-]([0-9,\,,\.]+)[\+,\-,\)])|(^([0-9,\,,\.]+)[\+,\-,\)])"
    Dim colConstMatches As MatchCollection
    Set colConstMatches = objRegExp.Execute(str)
    objRegExp.Pattern = "[\(,\+,\-]([0-9,\,,\.]+)$"
    Dim colConstMatchesEndLine As MatchCollection
    Set colConstMatchesEndLine = objRegExp.Execute(str)

    k = 0
    'Постановка размерных коэффициентов после свободных констант
'    For Each objMatch In colConstMatches
'        If inTrig(objMatch.FirstIndex + 4, col) = False Then
'            str1 = Mid(str, 1, objMatch.FirstIndex + objMatch.Length + Len(dimK) * k - 1)
'            str2 = Mid(str, objMatch.FirstIndex + objMatch.Length + Len(dimK) * k)
'            str = str1 & dimK & str2
'            k = k + 1
'        End If
'    Next objMatch

'    'Обработка случая, когда константа стоит в конце формулы
'    If (colConstMatchesEndLine.Count > 0) Then
'        str = str & dimK
'    End If

    parseFormula = "(" & str & ")" & dimK
End Function

Public Function getTrigBoundaries(str1 As String) As Collection

    Dim pos As Integer
    Dim c As String

    pos = 0
    c = ""

    Dim openBr As Integer
    Dim closeBr As Integer
    Dim exprLen As Integer
    Dim enterPos As Integer

    openBr = 1
    closeBr = 0
    exprLen = 0
    enterPos = 0

    Dim col As New Collection
    Dim boundNr As String
    boundNr = "1"

    pos = InStr(1, str1, "sin(")
    Do While pos > 0
       Do While (openBr > closeBr)
            c = Mid(str1, pos + exprLen + 4, 1)
            If (c = "(") Then
                openBr = openBr + 1
            ElseIf (c = ")") Then
                closeBr = closeBr + 1
            End If
            exprLen = exprLen + 1
        Loop
        enterPos = pos + exprLen + 3
        col.Add pos, boundNr
        boundNr = str(Val(boundNr) + 1)
        col.Add enterPos, boundNr
        boundNr = str(Val(boundNr) + 1)
        pos = InStr(enterPos, str1, "sin(")
    Loop

    pos = 0
    openBr = 1
    closeBr = 0
    exprLen = 0
    enterPos = 0

    pos = InStr(1, str1, "cos(")
    Do While pos > 0
       Do While (openBr > closeBr)
            c = Mid(str1, pos + exprLen + 4, 1)
            If (c = "(") Then
                openBr = openBr + 1
            ElseIf (c = ")") Then
                closeBr = closeBr + 1
            End If
            exprLen = exprLen + 1
        Loop
        enterPos = pos + exprLen + 3
        col.Add pos, boundNr
        boundNr = str(Val(boundNr) + 1)
        col.Add enterPos, boundNr
        boundNr = str(Val(boundNr) + 1)
        pos = InStr(enterPos, str1, "cos(")
    Loop

    pos = 0
    openBr = 1
    closeBr = 0
    exprLen = 0
    enterPos = 0

    pos = InStr(1, str1, "tan(")
    Do While pos > 0
        If (Mid(str1, pos - 1, 1) <> "a") Then 'обработка atan
            Do While (openBr > closeBr)
                 c = Mid(str1, pos + exprLen + 4, 1)
                 If (c = "(") Then
                     openBr = openBr + 1
                 ElseIf (c = ")") Then
                     closeBr = closeBr + 1
                 End If
                 exprLen = exprLen + 1
             Loop
             enterPos = pos + exprLen + 3
             col.Add pos, boundNr
             boundNr = str(Val(boundNr) + 1)
             col.Add enterPos, boundNr
             boundNr = str(Val(boundNr) + 1)
         Else
            enterPos = pos + 1
         End If
         pos = InStr(enterPos, str1, "tan(")
    Loop

    Set getTrigBoundaries = col

End Function

Public Function inTrig(pos As Integer, col As Collection) As Boolean

    inTrig = False
    Dim i As Integer
    If (col.Count > 0) Then
        For i = 1 To col.Count
            If pos > col.Item(i) And pos < col.Item(i + 1) Then
                inTrig = True
            End If
            i = i + 1
        Next i
    End If

End Function

Public Function sortCol(col As Collection) As Collection

    Dim newCol As New Collection

    Dim i As Integer
    Dim j As Integer
    Dim minEl As Integer
    Dim minIn As Integer
    Dim swapEl As Integer
    minEl = 10000
    For i = 1 To col.Count - 1

        For j = 1 To col.Count
            If col.Item(j) < minEl Then
                minEl = col.Item(j)
                minIn = j
            End If
        Next j
        newCol.Add col.Item(minIn)
        col.Remove minIn
        minEl = 10000
    Next i
    If col.Count > 0 Then
        newCol.Add col.Item(1)
    End If
    Set sortCol = newCol

End Function

Attribute VB_Name = "GDML2CATIA"
Sub CATMain()

    formGDML2CATIA.Show vbModeless

End Sub

Attribute VB_Name = "Steps"
Option Explicit

Const STEPADD = 0.002
Const CIRCSHIFT = 0.02
Const PI = 3.14159265358979

Dim PartVolumePair As Collection
' Key - part number ("G4_World"), item - pointer to the document ("G4_World.CATPart")

' Profiling
Dim timer As New CTimer

'flag = False   -   the solid is not the shape of volume
'flag = True    -   the solid is the upper node in the boolean tree and hence it is the shape to be applyed to the volume
Public Sub CreateSolids_recur(GDML As DOMDocument60, prtDoc As PartDocument, solidName As String, path As String, flag As Boolean)

    Dim prt As Part
    Dim bds As Bodies
    Set prt = prtDoc.Part
    Set bds = prt.Bodies

    Dim i As Integer
    Dim j As Integer
    Dim firstRefIndex As Integer
    Dim secondRefIndex As Integer

    Dim posIndex As Integer
    Dim rotIndex As Integer
    Dim posNode As IXMLDOMNode
    Dim rotNode As IXMLDOMNode

    Dim defineNode As IXMLDOMNode
    Dim defineNodesList As IXMLDOMNodeList
    Set defineNode = GDML.getElementsByTagName("define").Item(0)
    Set defineNodesList = defineNode.childNodes


    Dim solidNodes As IXMLDOMNodeList
    Dim solidNode As IXMLDOMNode
    Dim solidList As IXMLDOMNodeList
    Set solidNodes = GDML.getElementsByTagName("solids")
    Set solidNode = solidNodes.Item(0)
    Set solidList = solidNode.childNodes

    For j = 0 To solidList.Length - 1
        If solidList.Item(j).Attributes.getNamedItem("name").nodeValue = solidName Then
            Exit For
        End If
    Next

    Dim newBody As Body
    Dim shpFactory As ShapeFactory

    Dim minR As Double
    Dim maxR As Double
    Dim lowZ As Double
    Dim upZ As Double

        ' Убрал перевод параметров в строку
        Select Case solidList.Item(j).nodeName

        Case "arb8"
            Set newBody = CreateArb8(path, prtDoc, solidList.Item(j).Attributes.getNamedItem("v1x").nodeValue, _
                                                   solidList.Item(j).Attributes.getNamedItem("v1y").nodeValue, _
                                                   solidList.Item(j).Attributes.getNamedItem("v2x").nodeValue, _
                                                   solidList.Item(j).Attributes.getNamedItem("v2y").nodeValue, _
                                                   solidList.Item(j).Attributes.getNamedItem("v3x").nodeValue, _
                                                   solidList.Item(j).Attributes.getNamedItem("v3y").nodeValue, _
                                                   solidList.Item(j).Attributes.getNamedItem("v4x").nodeValue, _
                                                   solidList.Item(j).Attributes.getNamedItem("v4y").nodeValue, _
                                                   solidList.Item(j).Attributes.getNamedItem("v5x").nodeValue, _
                                                   solidList.Item(j).Attributes.getNamedItem("v5y").nodeValue, _
                                                   solidList.Item(j).Attributes.getNamedItem("v6x").nodeValue, _
                                                   solidList.Item(j).Attributes.getNamedItem("v6y").nodeValue, _
                                                   solidList.Item(j).Attributes.getNamedItem("v7x").nodeValue, _
                                                   solidList.Item(j).Attributes.getNamedItem("v7y").nodeValue, _
                                                   solidList.Item(j).Attributes.getNamedItem("v8x").nodeValue, _
                                                   solidList.Item(j).Attributes.getNamedItem("v8y").nodeValue, _
                                                   solidList.Item(j).Attributes.getNamedItem("dz").nodeValue, _
                                                   solidList.Item(j).Attributes.getNamedItem("lunit").nodeValue)
            newBody.name = "Body." & solidList.Item(j).Attributes.getNamedItem("name").nodeValue
            If flag = True Then ChangePartBody prtDoc, newBody

        Case "box"
            Set newBody = CreateBox(path, prtDoc, solidList.Item(j).Attributes.getNamedItem("x").nodeValue, _
                                                  solidList.Item(j).Attributes.getNamedItem("y").nodeValue, _
                                                  solidList.Item(j).Attributes.getNamedItem("z").nodeValue, _
                                                  solidList.Item(j).Attributes.getNamedItem("lunit").nodeValue)
            newBody.name = "Body." & solidList.Item(j).Attributes.getNamedItem("name").nodeValue
            If flag = True Then ChangePartBody prtDoc, newBody
        Case "cone"
            Set newBody = CreateCons(path, prtDoc, solidList.Item(j).Attributes.getNamedItem("rmin1").nodeValue, _
                                                   solidList.Item(j).Attributes.getNamedItem("rmax1").nodeValue, _
                                                   solidList.Item(j).Attributes.getNamedItem("rmin2").nodeValue, _
                                                   solidList.Item(j).Attributes.getNamedItem("rmax2").nodeValue, _
                                                   solidList.Item(j).Attributes.getNamedItem("z").nodeValue, _
                                                   solidList.Item(j).Attributes.getNamedItem("startphi").nodeValue, _
                                                   solidList.Item(j).Attributes.getNamedItem("deltaphi").nodeValue, _
                                                    solidList.Item(j).Attributes.getNamedItem("lunit").nodeValue, _
                                                    solidList.Item(j).Attributes.getNamedItem("aunit").nodeValue, False)

            newBody.name = "Body." & solidList.Item(j).Attributes.getNamedItem("name").nodeValue
            If flag = True Then ChangePartBody prtDoc, newBody
        Case "ellipsoid"
            Set newBody = CreateEllipsoid(path, prtDoc, solidList.Item(j).Attributes.getNamedItem("ax").nodeValue, _
                                                        solidList.Item(j).Attributes.getNamedItem("by").nodeValue, _
                                                        solidList.Item(j).Attributes.getNamedItem("cz").nodeValue, _
                                                        solidList.Item(j).Attributes.getNamedItem("zcut1").nodeValue, _
                                                        solidList.Item(j).Attributes.getNamedItem("zcut2").nodeValue, _
                                                        solidList.Item(j).Attributes.getNamedItem("lunit").nodeValue)

            newBody.name = "Body." & solidList.Item(j).Attributes.getNamedItem("name").nodeValue
            If flag = True Then ChangePartBody prtDoc, newBody
        Case "elcone"
            Set newBody = CreateEllipticalCone(path, prtDoc, solidList.Item(j).Attributes.getNamedItem("dx").nodeValue, _
                                                             solidList.Item(j).Attributes.getNamedItem("dy").nodeValue, _
                                                             solidList.Item(j).Attributes.getNamedItem("zmax").nodeValue, _
                                                             solidList.Item(j).Attributes.getNamedItem("zcut").nodeValue, _
                                                            solidList.Item(j).Attributes.getNamedItem("lunit").nodeValue)

            newBody.name = "Body." & solidList.Item(j).Attributes.getNamedItem("name").nodeValue
            If flag = True Then ChangePartBody prtDoc, newBody
        Case "eltube"
            Set newBody = CreateEllipticalTube(path, prtDoc, solidList.Item(j).Attributes.getNamedItem("dx").nodeValue, _
                                                             solidList.Item(j).Attributes.getNamedItem("dy").nodeValue, _
                                                             solidList.Item(j).Attributes.getNamedItem("dz").nodeValue, _
                                                            solidList.Item(j).Attributes.getNamedItem("lunit").nodeValue)

            newBody.name = "Body." & solidList.Item(j).Attributes.getNamedItem("name").nodeValue
            If flag = True Then ChangePartBody prtDoc, newBody
        Case "hedra"
            Set newBody = CreateHedra(path, prtDoc, solidList.Item(j).Attributes.getNamedItem("rmin1").nodeValue, _
                                                   solidList.Item(j).Attributes.getNamedItem("rmax1").nodeValue, _
                                                   solidList.Item(j).Attributes.getNamedItem("rmin2").nodeValue, _
                                                   solidList.Item(j).Attributes.getNamedItem("rmax2").nodeValue, _
                                                   solidList.Item(j).Attributes.getNamedItem("z").nodeValue, _
                                                   solidList.Item(j).Attributes.getNamedItem("startphi").nodeValue, _
                                                   solidList.Item(j).Attributes.getNamedItem("deltaphi").nodeValue, _
                                                   solidList.Item(j).Attributes.getNamedItem("numsides").nodeValue, _
                                                    solidList.Item(j).Attributes.getNamedItem("lunit").nodeValue, _
                                                    solidList.Item(j).Attributes.getNamedItem("aunit").nodeValue, False)

            newBody.name = "Body." & solidList.Item(j).Attributes.getNamedItem("name").nodeValue
            If flag = True Then ChangePartBody prtDoc, newBody
    '----------------------------------------------------------------------------------------------------------------------------------
        Case "hype"
            Set newBody = CreateTubs(path, prtDoc, "0", "360", _
                                                    solidList.Item(j).Attributes.getNamedItem("rmin").nodeValue, _
                                                    solidList.Item(j).Attributes.getNamedItem("rmax").nodeValue, _
                                                    solidList.Item(j).Attributes.getNamedItem("z").nodeValue, _
                                                    solidList.Item(j).Attributes.getNamedItem("lunit").nodeValue, _
                                                    solidList.Item(j).Attributes.getNamedItem("aunit").nodeValue)
            newBody.name = "Body." & solidList.Item(j).Attributes.getNamedItem("name").nodeValue
            If flag = True Then ChangePartBody prtDoc, newBody
    '----------------------------------------------------------------------------------------------------------------------------------
        Case "orb"
            Set newBody = CreateOrb(path, prtDoc, str(Val(solidList.Item(j).Attributes.getNamedItem("r").nodeValue)), _
                                                          solidList.Item(j).Attributes.getNamedItem("lunit").nodeValue)

            newBody.name = "Body." & solidList.Item(j).Attributes.getNamedItem("name").nodeValue
            If flag = True Then ChangePartBody prtDoc, newBody
        Case "para"
            Set newBody = CreatePara(path, prtDoc, solidList.Item(j).Attributes.getNamedItem("x").nodeValue, _
                                                   solidList.Item(j).Attributes.getNamedItem("y").nodeValue, _
                                                   solidList.Item(j).Attributes.getNamedItem("z").nodeValue, _
                                                   solidList.Item(j).Attributes.getNamedItem("alpha").nodeValue, _
                                                   solidList.Item(j).Attributes.getNamedItem("theta").nodeValue, _
                                                   solidList.Item(j).Attributes.getNamedItem("phi").nodeValue, _
                                                    solidList.Item(j).Attributes.getNamedItem("lunit").nodeValue, _
                                                    solidList.Item(j).Attributes.getNamedItem("aunit").nodeValue)

            newBody.name = "Body." & solidList.Item(j).Attributes.getNamedItem("name").nodeValue
            If flag = True Then ChangePartBody prtDoc, newBody
        Case "polycone"
            Set newBody = CreatePolycone(path, prtDoc, solidList.Item(j))
            newBody.name = "Body." & solidList.Item(j).Attributes.getNamedItem("name").nodeValue
            If flag = True Then ChangePartBody prtDoc, newBody
        Case "polyhedra"
            Set newBody = CreatePolyhedra(path, prtDoc, solidList.Item(j))
            newBody.name = "Body." & solidList.Item(j).Attributes.getNamedItem("name").nodeValue
            If flag = True Then ChangePartBody prtDoc, newBody
        Case "sphere"
            Set newBody = CreateSphere(path, prtDoc, solidList.Item(j).Attributes.getNamedItem("rmin").nodeValue, _
                                                     solidList.Item(j).Attributes.getNamedItem("rmax").nodeValue, _
                                                     solidList.Item(j).Attributes.getNamedItem("startphi").nodeValue, _
                                                     solidList.Item(j).Attributes.getNamedItem("deltaphi").nodeValue, _
                                                     solidList.Item(j).Attributes.getNamedItem("starttheta").nodeValue, _
                                                     solidList.Item(j).Attributes.getNamedItem("deltatheta").nodeValue, _
                                                    solidList.Item(j).Attributes.getNamedItem("lunit").nodeValue, _
                                                    solidList.Item(j).Attributes.getNamedItem("aunit").nodeValue)

            newBody.name = "Body." & solidList.Item(j).Attributes.getNamedItem("name").nodeValue
            If flag = True Then ChangePartBody prtDoc, newBody
        Case "torus"
            Set newBody = CreateTorus(path, prtDoc, solidList.Item(j).Attributes.getNamedItem("rmin").nodeValue, _
                                                    solidList.Item(j).Attributes.getNamedItem("rmax").nodeValue, _
                                                    solidList.Item(j).Attributes.getNamedItem("rtor").nodeValue, _
                                                    solidList.Item(j).Attributes.getNamedItem("startphi").nodeValue, _
                                                    solidList.Item(j).Attributes.getNamedItem("deltaphi").nodeValue, _
                                                    solidList.Item(j).Attributes.getNamedItem("lunit").nodeValue, _
                                                    solidList.Item(j).Attributes.getNamedItem("aunit").nodeValue)

            newBody.name = "Body." & solidList.Item(j).Attributes.getNamedItem("name").nodeValue
            If flag = True Then ChangePartBody prtDoc, newBody
        Case "trap"
            Set newBody = CreateTrap(path, prtDoc, solidList.Item(j).Attributes.getNamedItem("z").nodeValue, _
                                                   solidList.Item(j).Attributes.getNamedItem("theta").nodeValue, _
                                                   solidList.Item(j).Attributes.getNamedItem("phi").nodeValue, _
                                                   solidList.Item(j).Attributes.getNamedItem("y1").nodeValue, _
                                                   solidList.Item(j).Attributes.getNamedItem("x1").nodeValue, _
                                                   solidList.Item(j).Attributes.getNamedItem("x2").nodeValue, _
                                                   solidList.Item(j).Attributes.getNamedItem("alpha1").nodeValue, _
                                                   solidList.Item(j).Attributes.getNamedItem("y2").nodeValue, _
                                                   solidList.Item(j).Attributes.getNamedItem("x3").nodeValue, _
                                                   solidList.Item(j).Attributes.getNamedItem("x4").nodeValue, _
                                                    solidList.Item(j).Attributes.getNamedItem("lunit").nodeValue, _
                                                    solidList.Item(j).Attributes.getNamedItem("aunit").nodeValue)

            newBody.name = "Body." & solidList.Item(j).Attributes.getNamedItem("name").nodeValue
            If flag = True Then ChangePartBody prtDoc, newBody
        Case "trd"
            Set newBody = CreateTrd(path, prtDoc, solidList.Item(j).Attributes.getNamedItem("x1").nodeValue, _
                                                  solidList.Item(j).Attributes.getNamedItem("x2").nodeValue, _
                                                  solidList.Item(j).Attributes.getNamedItem("y1").nodeValue, _
                                                  solidList.Item(j).Attributes.getNamedItem("y2").nodeValue, _
                                                  solidList.Item(j).Attributes.getNamedItem("z").nodeValue, _
                                                    solidList.Item(j).Attributes.getNamedItem("lunit").nodeValue)

            newBody.name = "Body." & solidList.Item(j).Attributes.getNamedItem("name").nodeValue
            If flag = True Then ChangePartBody prtDoc, newBody
        Case "tube"
            Set newBody = CreateTubs(path, prtDoc, solidList.Item(j).Attributes.getNamedItem("rmin").nodeValue, _
                                                   solidList.Item(j).Attributes.getNamedItem("rmax").nodeValue, _
                                                   solidList.Item(j).Attributes.getNamedItem("z").nodeValue, _
                                                   solidList.Item(j).Attributes.getNamedItem("startphi").nodeValue, _
                                                   solidList.Item(j).Attributes.getNamedItem("deltaphi").nodeValue, _
                                                    solidList.Item(j).Attributes.getNamedItem("lunit").nodeValue, _
                                                    solidList.Item(j).Attributes.getNamedItem("aunit").nodeValue)

            newBody.name = "Body." & solidList.Item(j).Attributes.getNamedItem("name").nodeValue
            If flag = True Then ChangePartBody prtDoc, newBody
        Case "twistedbox"
            Set newBody = CreateTwistedBox(path, prtDoc, solidList.Item(j).Attributes.getNamedItem("PhiTwist").nodeValue, _
                                                         solidList.Item(j).Attributes.getNamedItem("x").nodeValue, _
                                                         solidList.Item(j).Attributes.getNamedItem("y").nodeValue, _
                                                         solidList.Item(j).Attributes.getNamedItem("z").nodeValue, _
                                                        solidList.Item(j).Attributes.getNamedItem("lunit").nodeValue, _
                                                        solidList.Item(j).Attributes.getNamedItem("aunit").nodeValue)

            newBody.name = "Body." & solidList.Item(j).Attributes.getNamedItem("name").nodeValue
            If flag = True Then ChangePartBody prtDoc, newBody
        Case "twistedtrap"
            Set newBody = CreateTwistedTrap(path, prtDoc, solidList.Item(j).Attributes.getNamedItem("PhiTwist").nodeValue, _
                                                          solidList.Item(j).Attributes.getNamedItem("z").nodeValue, _
                                                          solidList.Item(j).Attributes.getNamedItem("Theta").nodeValue, _
                                                          solidList.Item(j).Attributes.getNamedItem("Phi").nodeValue, _
                                                          solidList.Item(j).Attributes.getNamedItem("y1").nodeValue, _
                                                          solidList.Item(j).Attributes.getNamedItem("x1").nodeValue, _
                                                          solidList.Item(j).Attributes.getNamedItem("x2").nodeValue, _
                                                          solidList.Item(j).Attributes.getNamedItem("y2").nodeValue, _
                                                          solidList.Item(j).Attributes.getNamedItem("x3").nodeValue, _
                                                          solidList.Item(j).Attributes.getNamedItem("x4").nodeValue, _
                                                          solidList.Item(j).Attributes.getNamedItem("Alph").nodeValue, _
                                                            solidList.Item(j).Attributes.getNamedItem("lunit").nodeValue, _
                                                            solidList.Item(j).Attributes.getNamedItem("aunit").nodeValue)

            newBody.name = "Body." & solidList.Item(j).Attributes.getNamedItem("name").nodeValue
            If flag = True Then ChangePartBody prtDoc, newBody
        Case "twistedtrd"
            Set newBody = CreateTwistedTrd(path, prtDoc, solidList.Item(j).Attributes.getNamedItem("x1").nodeValue, _
                                                         solidList.Item(j).Attributes.getNamedItem("x2").nodeValue, _
                                                         solidList.Item(j).Attributes.getNamedItem("y1").nodeValue, _
                                                         solidList.Item(j).Attributes.getNamedItem("y2").nodeValue, _
                                                         solidList.Item(j).Attributes.getNamedItem("z").nodeValue, _
                                                         solidList.Item(j).Attributes.getNamedItem("PhiTwist").nodeValue, _
                                                        solidList.Item(j).Attributes.getNamedItem("lunit").nodeValue, _
                                                        solidList.Item(j).Attributes.getNamedItem("aunit").nodeValue)

            newBody.name = "Body." & solidList.Item(j).Attributes.getNamedItem("name").nodeValue
            If flag = True Then ChangePartBody prtDoc, newBody
        Case "twistedtubs"
            Set newBody = CreateTwistedTubs(path, prtDoc, solidList.Item(j).Attributes.getNamedItem("twistedangle").nodeValue, _
                                                          solidList.Item(j).Attributes.getNamedItem("endinnerrad").nodeValue, _
                                                          solidList.Item(j).Attributes.getNamedItem("endouterrad").nodeValue, _
                                                          solidList.Item(j).Attributes.getNamedItem("zlen").nodeValue, _
                                                          solidList.Item(j).Attributes.getNamedItem("phi").nodeValue, _
                                                        solidList.Item(j).Attributes.getNamedItem("lunit").nodeValue, _
                                                        solidList.Item(j).Attributes.getNamedItem("aunit").nodeValue)

            newBody.name = "Body." & solidList.Item(j).Attributes.getNamedItem("name").nodeValue
            If flag = True Then ChangePartBody prtDoc, newBody
        Case "xtru"
            Set newBody = CreateXtru(path, prtDoc, solidList.Item(j).Attributes.getNamedItem("lunit").nodeValue, solidList.Item(j))
            newBody.name = "Body." & solidList.Item(j).Attributes.getNamedItem("name").nodeValue
            If flag = True Then ChangePartBody prtDoc, newBody

        Case "union", "subtraction", "intersection"
            For i = 0 To solidList.Item(j).childNodes.Length - 1
                If solidList.Item(j).childNodes.Item(i).nodeName = "first" Then
                    firstRefIndex = i
                ElseIf solidList.Item(j).childNodes.Item(i).nodeName = "second" Then
                    secondRefIndex = i
                ElseIf solidList.Item(j).childNodes.Item(i).nodeName = "position" Or _
                        solidList.Item(j).childNodes.Item(i).nodeName = "positionref" Then
                    posIndex = i
                ElseIf solidList.Item(j).childNodes.Item(i).nodeName = "rotation" Or _
                        solidList.Item(j).childNodes.Item(i).nodeName = "rotationref" Then
                    rotIndex = i
                End If
            Next

            'process creating operands
            CreateSolids_recur GDML, prtDoc, solidList.Item(j).childNodes.Item(firstRefIndex).Attributes.getNamedItem("ref").nodeValue, path, False
            CreateSolids_recur GDML, prtDoc, solidList.Item(j).childNodes.Item(secondRefIndex).Attributes.getNamedItem("ref").nodeValue, path, False

            'process rotation of the second operand
            ' edited on 22.02.11
            ' signes changed and the order of the angles
            ' edited on 31.01.12
            ' deleted the minuses
            Select Case solidList.Item(j).childNodes.Item(rotIndex).nodeName
                Case "rotation"
                    Set rotNode = solidList.Item(j).childNodes.Item(rotIndex)
                    If (rotNode.Attributes.getNamedItem("z").nodeValue <> "0" And rotNode.Attributes.getNamedItem("z").nodeValue <> "(0)*2") Then _
                        AddRotation bds.Item("Body." & solidList.Item(j).childNodes.Item(secondRefIndex).Attributes.getNamedItem("ref").nodeValue), _
                                            prtDoc, "Z", rotNode.Attributes.getNamedItem("z").nodeValue, _
                                            rotNode.Attributes.getNamedItem("unit").nodeValue
                    If (rotNode.Attributes.getNamedItem("y").nodeValue <> "0" And rotNode.Attributes.getNamedItem("y").nodeValue <> "(0)*2") Then _
                        AddRotation bds.Item("Body." & solidList.Item(j).childNodes.Item(secondRefIndex).Attributes.getNamedItem("ref").nodeValue), _
                                            prtDoc, "Y", rotNode.Attributes.getNamedItem("y").nodeValue, _
                                            rotNode.Attributes.getNamedItem("unit").nodeValue
                    If (rotNode.Attributes.getNamedItem("x").nodeValue <> "0" And rotNode.Attributes.getNamedItem("x").nodeValue <> "(0)*2") Then _
                        AddRotation bds.Item("Body." & solidList.Item(j).childNodes.Item(secondRefIndex).Attributes.getNamedItem("ref").nodeValue), _
                                            prtDoc, "X", rotNode.Attributes.getNamedItem("x").nodeValue, _
                                            rotNode.Attributes.getNamedItem("unit").nodeValue
                Case "rotationref"
' TODO optimize using key-collection the same way it is done for physvol
                    For i = 0 To defineNodesList.Length - 1
                        If Not (defineNodesList.Item(i).nodeName = "#comment") Then
                            If defineNodesList.Item(i).nodeName = "rotation" And _
                                solidList.Item(j).childNodes.Item(rotIndex).Attributes.getNamedItem("ref").nodeValue = _
                                defineNodesList.Item(i).Attributes.getNamedItem("name").nodeValue Then
                                Set rotNode = defineNodesList.Item(i)
                                Exit For
                            End If
                        End If
                    Next
                    If (rotNode.Attributes.getNamedItem("z").nodeValue <> "0" And rotNode.Attributes.getNamedItem("z").nodeValue <> "(0)*2") Then _
                        AddRotation bds.Item("Body." & solidList.Item(j).childNodes.Item(secondRefIndex).Attributes.getNamedItem("ref").nodeValue), _
                                            prtDoc, "Z", rotNode.Attributes.getNamedItem("z").nodeValue, _
                                            rotNode.Attributes.getNamedItem("unit").nodeValue
                    If (rotNode.Attributes.getNamedItem("y").nodeValue <> "0" And rotNode.Attributes.getNamedItem("y").nodeValue <> "(0)*2") Then _
                        AddRotation bds.Item("Body." & solidList.Item(j).childNodes.Item(secondRefIndex).Attributes.getNamedItem("ref").nodeValue), _
                                            prtDoc, "Y", rotNode.Attributes.getNamedItem("y").nodeValue, _
                                            rotNode.Attributes.getNamedItem("unit").nodeValue
                    If (rotNode.Attributes.getNamedItem("x").nodeValue <> "0" And rotNode.Attributes.getNamedItem("x").nodeValue <> "(0)*2") Then _
                        AddRotation bds.Item("Body." & solidList.Item(j).childNodes.Item(secondRefIndex).Attributes.getNamedItem("ref").nodeValue), _
                                            prtDoc, "X", rotNode.Attributes.getNamedItem("x").nodeValue, _
                                            rotNode.Attributes.getNamedItem("unit").nodeValue
            End Select

            'process positioning of the first operand
            Select Case solidList.Item(j).childNodes.Item(posIndex).nodeName
                Case "position"
                    Set posNode = solidList.Item(j).childNodes.Item(posIndex)
                    If posNode.Attributes.getNamedItem("x").nodeValue <> 0 Or posNode.Attributes.getNamedItem("y").nodeValue <> 0 Or _
                                                                                    posNode.Attributes.getNamedItem("z").nodeValue <> 0 Then _
                        AddTranslation bds.Item("Body." & solidList.Item(j).childNodes.Item(secondRefIndex).Attributes.getNamedItem("ref").nodeValue), prtDoc, _
                                                posNode.Attributes.getNamedItem("x").nodeValue, _
                                                posNode.Attributes.getNamedItem("y").nodeValue, _
                                                posNode.Attributes.getNamedItem("z").nodeValue, _
                                                posNode.Attributes.getNamedItem("unit").nodeValue
                Case "positionref"
' TODO optimize using key-collection the same way it is done for physvol
                    For i = 0 To defineNodesList.Length - 1
                        If Not (defineNodesList.Item(i).nodeName = "#comment") Then
                            If defineNodesList.Item(i).nodeName = "position" And _
                                solidList.Item(j).childNodes.Item(posIndex).Attributes.getNamedItem("ref").nodeValue = _
                                defineNodesList.Item(i).Attributes.getNamedItem("name").nodeValue Then
                                Set posNode = defineNodesList.Item(i)
                                Exit For
                            End If
                        End If
                    Next
                    If posNode.Attributes.getNamedItem("x").nodeValue <> 0 Or posNode.Attributes.getNamedItem("y").nodeValue <> 0 Or _
                                                                                    posNode.Attributes.getNamedItem("z").nodeValue <> 0 Then _
                        AddTranslation bds.Item("Body." & solidList.Item(j).childNodes.Item(secondRefIndex).Attributes.getNamedItem("ref").nodeValue), prtDoc, _
                                                posNode.Attributes.getNamedItem("x").nodeValue, _
                                                posNode.Attributes.getNamedItem("y").nodeValue, _
                                                posNode.Attributes.getNamedItem("z").nodeValue, _
                                                posNode.Attributes.getNamedItem("unit").nodeValue
            End Select

            Select Case solidList.Item(j).nodeName
                Case "union"
                     Set newBody = CreateUnion(bds.Item("Body." & solidList.Item(j).childNodes.Item(firstRefIndex).Attributes.getNamedItem("ref").nodeValue), _
                                bds.Item("Body." & solidList.Item(j).childNodes.Item(secondRefIndex).Attributes.getNamedItem("ref").nodeValue), _
                                prtDoc, "Body." & solidList.Item(j).Attributes.getNamedItem("name").nodeValue)
                Case "subtraction"
                     Set newBody = CreateSubtracion(bds.Item("Body." & solidList.Item(j).childNodes.Item(firstRefIndex).Attributes.getNamedItem("ref").nodeValue), _
                                bds.Item("Body." & solidList.Item(j).childNodes.Item(secondRefIndex).Attributes.getNamedItem("ref").nodeValue), _
                                prtDoc, "Body." & solidList.Item(j).Attributes.getNamedItem("name").nodeValue)
                Case "intersection"
                     Set newBody = CreateIntersection(bds.Item("Body." & solidList.Item(j).childNodes.Item(firstRefIndex).Attributes.getNamedItem("ref").nodeValue), _
                                bds.Item("Body." & solidList.Item(j).childNodes.Item(secondRefIndex).Attributes.getNamedItem("ref").nodeValue), _
                                prtDoc, "Body." & solidList.Item(j).Attributes.getNamedItem("name").nodeValue)
            End Select
            If flag = True Then ChangePartBody prtDoc, newBody

        Case Else
'            MsgBox "Unsupported tag " & solidList.Item(j).nodeName & " found in the GDML file in solids section." & Chr(13) & "Trying to skip it. Error may occur further.", vbExclamation
    End Select

End Sub

Public Sub ChangePartBody(prtDoc As PartDocument, newBody As Body)

    Dim sel As Selection
    Set sel = CATIA.ActiveDocument.Selection

    prtDoc.Part.Bodies.Item("PartBody").name = "ToBeDeleted"
    prtDoc.Part.MainBody = newBody
    prtDoc.Part.MainBody.name = "PartBody"
    sel.Clear

    sel.Add prtDoc.Part.Bodies.GetItem("ToBeDeleted")

    'For j = 1 To prtDoc.Part.Bodies.Count
    '    If prtDoc.Part.Bodies.Item(j).Name = "ToBeDeleted" Then
    '        sel.Add prtDoc.Part.Bodies.Item("ToBeDeleted")
    '        Exit For
    '    End If
    'Next
    If sel.Count2 > 0 Then sel.Delete

End Sub

Public Sub CreateGeometry(GDML As DOMDocument60, path As String)

    Dim visPropSet As VisPropertySet
    Dim prodDoc As ProductDocument
    Dim prod As Product
    Dim subProds As Products
    Dim i As Integer
    Dim j As Integer
    Dim newComp As Product
    Dim curPrtDoc As PartDocument
    Dim pubs As Publications
    Dim ref As Reference
    Dim sel

    Set prodDoc = CATIA.ActiveDocument
    Set prod = prodDoc.Product
    Set subProds = prod.Products
    Set sel = CATIA.ActiveDocument.Selection
    Set visPropSet = sel.VisProperties

    Set PartVolumePair = New Collection

    Dim struct As IXMLDOMNodeList
    Set struct = GDML.getElementsByTagName("structure")
    Dim structureChildes As IXMLDOMNodeList
    Set structureChildes = struct.Item(0).childNodes

    For i = 0 To structureChildes.Length - 1

        If Not (structureChildes.Item(i).nodeName = "#comment") Then
            Set newComp = subProds.AddNewComponent("Part", "")
            newComp.PartNumber = structureChildes.Item(i).Attributes.getNamedItem("name").nodeValue
            newComp.name = structureChildes.Item(i).Attributes.getNamedItem("name").nodeValue & ".1"

            Set curPrtDoc = newComp.ReferenceProduct.Parent
            PartVolumePair.Add curPrtDoc, newComp.PartNumber

            'hide standard planes
            sel.Clear
            sel.Add curPrtDoc.Part.OriginElements.PlaneXY
            sel.Add curPrtDoc.Part.OriginElements.PlaneZX
            sel.Add curPrtDoc.Part.OriginElements.PlaneYZ
            visPropSet.SetShow catVisPropertyNoShowAttr
            sel.Clear

            'create geometry
            Dim solidName As String

            'Find corresponding shape NAME
' TODO optimize using key-collection the same way it is done for physvol positionref/rotationref
            For j = 0 To structureChildes.Item(i).childNodes.Length - 1
                If structureChildes.Item(i).childNodes.Item(j).nodeName = "solidref" Then
                    solidName = structureChildes.Item(i).childNodes.Item(j).Attributes.getNamedItem("ref").nodeValue
                    Exit For
                End If
            Next j

            If structureChildes.Item(i).baseName = "volume" Then
                'Find correspondind SHAPE among all the solids, then parse all the boolean tree and create body
                CreateSolids_recur GDML, curPrtDoc, solidName, path, True
            ElseIf structureChildes.Item(i).baseName = "assembly" Then
                '
            End If

            ' GUI
            formGDML2CATIA.lblStatus.Caption = "Step 2/4. Creating solid " + solidName + _
                    vbNewLine + str(i + 1) + "/" + Trim(str(structureChildes.Length))

            'publicate PartBodies
            Set pubs = curPrtDoc.Product.Publications
            Set ref = newComp.CreateReferenceFromName(newComp.name & "/!PartBody")
            pubs.Add "PartBody"
            pubs.SetDirect "PartBody", ref
        End If
    Next i

End Sub

Public Sub ProcessMaterials(GDML As DOMDocument60)

    Dim i As Integer
    Dim j As Integer
    Dim matName As String
    Dim curPrtDoc As PartDocument
    Dim volums As IXMLDOMNodeList
    Dim params As Parameters

    Set volums = GDML.getElementsByTagName("volume") ' объединить в один цикл ?
    For i = 0 To volums.Length - 1
        For j = 0 To volums.Item(i).childNodes.Length - 1
            If volums.Item(i).childNodes.Item(j).nodeName = "materialref" Then Exit For
        Next
        matName = volums.Item(i).childNodes.Item(j).Attributes.getNamedItem("ref").nodeValue

        Set curPrtDoc = PartVolumePair.Item(volums.Item(i).Attributes.getNamedItem("name").nodeValue)
        Set params = curPrtDoc.Part.Parameters
        params.CreateString "Material", matName
        formGDML2CATIA.lblStatus.Caption = "Step 4/4. Creating materials " + _
            vbNewLine + str(i + 1) + "/" + Trim(str(volums.Length))
    Next i

    Set volums = GDML.getElementsByTagName("assembly")
    For i = 0 To volums.Length - 1
        Set curPrtDoc = PartVolumePair.Item(volums.Item(i).Attributes.getNamedItem("name").nodeValue)
        Set params = curPrtDoc.Part.Parameters
        params.CreateString "Material", "Assembly"
    Next i

End Sub

Public Sub ProcessInserting(GDML As DOMDocument60)

    Dim i As Integer
    Dim j As Integer
    Dim k As Integer
    Dim p As Integer
    Dim volums As IXMLDOMNodeList
    Dim chldvols As IXMLDOMNodeList
    Dim chldvol As IXMLDOMNode
    Dim chldVolName As String
    Dim mothVolName As String
    Dim pos As IXMLDOMNode
    Dim rot As IXMLDOMNode
    Dim x As String
    Dim y As String
    Dim z As String
    Dim xr As String
    Dim yr As String
    Dim zr As String
    Dim lunit As String
    Dim aunit As String
    Dim defineNode As IXMLDOMNode
    Dim defineNodesList As IXMLDOMNodeList

    'Set volums = GDML.getElementsByTagName("volume")
    Dim structure As IXMLDOMNodeList
    Set structure = GDML.getElementsByTagName("structure")
    Dim structureChildes As IXMLDOMNodeList
    Set structureChildes = structure.Item(0).childNodes

    Dim repNum As String
    Dim width As String
    Dim offset As String
    Dim direction As String
    Dim wunit As String
    Dim ounit As String
    Dim replAlongAxNode As IXMLDOMNode

    ' Prepare a map of defined positiones and rotations
    Set defineNode = GDML.getElementsByTagName("define").Item(0)
    Set defineNodesList = defineNode.childNodes
    Dim defPosColl As New Collection
    Dim defRotColl As New Collection
    For p = 0 To defineNodesList.Length - 1
        Select Case defineNodesList.Item(p).nodeName
            Case "position"
                defPosColl.Add defineNodesList.Item(p), defineNodesList.Item(p).Attributes.getNamedItem("name").nodeValue
            Case "rotation"
                defRotColl.Add defineNodesList.Item(p), defineNodesList.Item(p).Attributes.getNamedItem("name").nodeValue
        End Select
    Next p

    For i = 0 To structureChildes.Length - 1        ' loop through the volume tags (children of structure tag)

        Set chldvols = structureChildes.Item(i).childNodes      ' collection of physvol/replica/division tags

        ' Mother volume name (it does not depend on the type of the daughter - physvol/replica/division)
        mothVolName = structureChildes.Item(i).Attributes.getNamedItem("name").nodeValue

        For j = 0 To chldvols.Length - 1

            If (chldvols.Item(j).nodeName = "physvol") Or _
                (chldvols.Item(j).nodeName = "replicavol") Or _
                (chldvols.Item(j).nodeName = "divisionvol") Then

                ' Find k - reference to the daughter volume
                For k = 0 To chldvols.Item(j).childNodes.Length - 1
                    If chldvols.Item(j).childNodes.Item(k).nodeName = "volumeref" Then Exit For
                Next k
                ' Daughter volume name - use k here
                Set chldvol = chldvols.Item(j).childNodes.Item(k).Attributes.getNamedItem("ref")
                chldVolName = chldvol.nodeValue

            End If

            Select Case chldvols.Item(j).nodeName
            Case "physvol"

                x = "0"
                y = "0"
                z = "0"
                xr = "0"
                yr = "0"
                zr = "0"
                lunit = "mm"
                aunit = "deg"

                For k = 0 To chldvols.Item(j).childNodes.Length - 1
                    If chldvols.Item(j).childNodes.Item(k).nodeName = "position" Then
                        Set pos = chldvols.Item(j).childNodes.Item(k)
                        x = pos.Attributes.getNamedItem("x").nodeValue
                        y = pos.Attributes.getNamedItem("y").nodeValue
                        z = pos.Attributes.getNamedItem("z").nodeValue
                        lunit = pos.Attributes.getNamedItem("unit").nodeValue
                    ElseIf chldvols.Item(j).childNodes.Item(k).nodeName = "positionref" Then
                        Set pos = defPosColl.Item(chldvols.Item(j).childNodes.Item(k).Attributes.getNamedItem("ref").nodeValue)
                        x = pos.Attributes.getNamedItem("x").nodeValue
                        y = pos.Attributes.getNamedItem("y").nodeValue
                        z = pos.Attributes.getNamedItem("z").nodeValue
                        lunit = pos.Attributes.getNamedItem("unit").nodeValue
                    ElseIf chldvols.Item(j).childNodes.Item(k).nodeName = "rotation" Then
                        Set rot = chldvols.Item(j).childNodes.Item(k)
                        xr = rot.Attributes.getNamedItem("x").nodeValue
                        yr = rot.Attributes.getNamedItem("y").nodeValue
                        zr = rot.Attributes.getNamedItem("z").nodeValue
                        aunit = rot.Attributes.getNamedItem("unit").nodeValue
                    ElseIf chldvols.Item(j).childNodes.Item(k).nodeName = "rotationref" Then
                        Set rot = defRotColl.Item(chldvols.Item(j).childNodes.Item(k).Attributes.getNamedItem("ref").nodeValue)
                        xr = rot.Attributes.getNamedItem("x").nodeValue
                        yr = rot.Attributes.getNamedItem("y").nodeValue
                        zr = rot.Attributes.getNamedItem("z").nodeValue
                        aunit = rot.Attributes.getNamedItem("unit").nodeValue
                    End If
                Next k

                Insert chldVolName, mothVolName, x, y, z, xr, yr, zr, lunit, aunit
    
                formGDML2CATIA.lblStatus.Caption = "Step 3/4. Inserting " + chldVolName + " in " + mothVolName + _
                     vbNewLine + str(i + 1) + "/" + Trim(str(structureChildes.Length)) + "    " + str(j - 1) + "/" + Trim(str(chldvols.Length - 2))

            Case "replicavol"

                repNum = chldvols.Item(j).Attributes.getNamedItem("number").nodeValue

                ' Find <replicate_along_axis>
                For k = 0 To chldvols.Item(j).childNodes.Length - 1
                    If chldvols.Item(j).childNodes.Item(k).nodeName = "replicate_along_axis" Then Exit For
                Next k
                Set replAlongAxNode = chldvols.Item(j).childNodes.Item(k)

                For k = 0 To replAlongAxNode.childNodes.Length - 1
                    Select Case replAlongAxNode.childNodes.Item(k).nodeName
                        Case "direction"
                            ' !!!!!Надо переделать
                            direction = replAlongAxNode.childNodes.Item(k).Attributes.Item(0).nodeName
                            ' !!!!!---------------
                        Case "width"
                            width = replAlongAxNode.childNodes.Item(k).Attributes.getNamedItem("value").nodeValue
                            wunit = replAlongAxNode.childNodes.Item(k).Attributes.getNamedItem("unit").nodeValue
                        Case "offset"
                            offset = replAlongAxNode.childNodes.Item(k).Attributes.getNamedItem("value").nodeValue
                            ounit = replAlongAxNode.childNodes.Item(k).Attributes.getNamedItem("unit").nodeValue
                    End Select
                Next k

                Replicate chldVolName, mothVolName, repNum, direction, width, offset, wunit, ounit

                formGDML2CATIA.lblStatus.Caption = "Step 3/4. Replicating " + chldVolName + " in " + mothVolName + _
                    vbNewLine + str(i + 1) + "/" + Trim(str(structureChildes.Length)) + "    " + str(j - 1) + "/" + Trim(str(chldvols.Length - 2))

            Case "divisionvol"

                repNum = chldvols.Item(j).Attributes.getNamedItem("number").nodeValue
                width = chldvols.Item(j).Attributes.getNamedItem("width").nodeValue
                offset = chldvols.Item(j).Attributes.getNamedItem("offset").nodeValue
                direction = chldvols.Item(j).Attributes.getNamedItem("axis").nodeValue
                wunit = chldvols.Item(j).Attributes.getNamedItem("unit").nodeValue
                ounit = chldvols.Item(j).Attributes.getNamedItem("unit").nodeValue

                Replicate chldVolName, mothVolName, repNum, direction, width, offset, wunit, ounit

                formGDML2CATIA.lblStatus.Caption = "Step 3/4. Dividing " + chldVolName + " in " + mothVolName + _
                        vbNewLine + str(i + 1) + "/" + Trim(str(structureChildes.Length)) + "    " + str(j - 1) + "/" + Trim(str(chldvols.Length - 2))

            End Select

        Next j

        If structureChildes.Item(i).baseName = "assembly" Then
            ConstructAssemblyVolumeShape mothVolName
        End If

    Next i

End Sub

' Optimized as much as possible.
' Copies are created in a single copy-paste operation
' Add features are done one by one as there is no possibility to create
' many at once using factory. Check this.
Public Sub ConstructAssemblyVolumeShape(motherVolumeName As String)

    Dim i As Integer

    Dim partDoc As PartDocument
    Set partDoc = PartVolumePair.Item(motherVolumeName)

    ' Init selection
    Dim sel As Selection
    Set sel = CATIA.ActiveDocument.Selection
    sel.Clear

    ' Create copies
    Dim maxOrigBodyIndex As Integer
    maxOrigBodyIndex = partDoc.Part.Bodies.Count
    For i = 2 To maxOrigBodyIndex
        sel.Add partDoc.Part.Bodies.Item(i)
    Next i
    sel.Copy
    sel.PasteSpecial "CATPrtResult"
    sel.Clear

    Dim shpFac As ShapeFactory
    Set shpFac = partDoc.Part.ShapeFactory
    partDoc.Part.InWorkObject = partDoc.Part.Bodies.Item("PartBody")

    Dim add1 As Add
    For i = 2 To maxOrigBodyIndex
        Set add1 = shpFac.AddNewAdd(partDoc.Part.Bodies.Item(maxOrigBodyIndex + 1))
        add1.name = "Assembly_part." + Trim(str(i - 1))
    Next i

    ' The only update really needed!!!
    partDoc.Part.Update

End Sub

Public Function Insert(childVolumeName As String, _
            motherVolumeName As String, _
            x As String, y As String, z As String, _
            xr As String, yr As String, zr As String, _
            lunit As String, aunit As String) As Part

    Dim ProductDoc As ProductDocument
    Dim sel As Selection

    Set ProductDoc = CATIA.ActiveDocument
    Set sel = CATIA.ActiveDocument.Selection

    'coincidence_std_planes         ' is it needed here?

    ' Find the publication to be copied
    Dim pub As Publication
    Dim i As Integer
    For i = 1 To ProductDoc.Product.Products.Count
        If (ProductDoc.Product.Products.Item(i).PartNumber = childVolumeName) Then
            Set pub = ProductDoc.Product.Products.Item(i).Publications.Item("PartBody")
            Exit For
        End If
    Next i

    Dim partDoc As PartDocument
    Set partDoc = PartVolumePair.Item(motherVolumeName)

    ' Copy - paste - as result with link
    sel.Clear
    sel.Add pub
    sel.Copy
    sel.Clear
    sel.Add partDoc.Part
    sel.PasteSpecial "CATPrtResult"
    sel.Clear

    ' Rename recent copied body
    partDoc.Part.Bodies.Item(partDoc.Part.Bodies.Count).name = nameGenerate(partDoc, childVolumeName)

    ' Position
    ProcessBodyPosition partDoc.Part, partDoc.Part.Bodies.Item(partDoc.Part.Bodies.Count), x, y, z, xr, yr, zr, lunit, aunit

    partDoc.Part.Update

    Set Insert = partDoc.Part

End Function

' replica
Public Sub Replicate(childVolumeName As String, _
            motherVolumeName As String, _
            number As String, _
            direction As String, _
            width As String, _
            offset As String, _
            wunit As String, _
            ounit As String)

    'MsgBox childVolumeName & " into " & motherVolumeName & Chr(13) & _
            number & " times along " & direction & " axis" & Chr(13) & _
            "width = " & width & wunit & "    offset = " & offset & ounit

    ' Для сфер понадобилось из материнского шейпа вытащить pSphi
    Dim partDoc As PartDocument
    Dim params As Parameters
    Set partDoc = PartVolumePair.Item(motherVolumeName)
    Set params = partDoc.Part.Parameters

    Dim shapeName  As String
    Dim pSPhiVal As Double
    If (direction = "phi" Or direction = "kPhi") Then
        shapeName = partDoc.Part.Bodies.Item("PartBody").Shapes.Item(1).name
        pSPhiVal = Val(Replace(params.Item(partDoc.Part.name + "\PartBody\" + shapeName + "\pSPhi").ValueAsString, ",", "."))
    End If

    Dim x As String
    Dim y As String
    Dim z As String
    Dim rotZ As String
    x = "0"
    y = "0"
    z = "0"
    rotZ = "0"

    Select Case direction
        Case "x"
            x = str((Val(number) - 1) * 0.5 * Val(width))
        Case "kXAxis"
            x = str((Val(number) - 1) * 0.5 * Val(width))
        Case "y"
            y = str((Val(number) - 1) * 0.5 * Val(width))
        Case "kYAxis"
            y = str((Val(number) - 1) * 0.5 * Val(width))
        Case "z"
            z = str((Val(number) - 1) * 0.5 * Val(width))
        Case "kZAxis"
            z = str((Val(number) - 1) * 0.5 * Val(width))
' here are different shifts for visualising ------------------------------------------------------------------------------------------------
        Case "phi"
            x = str(CIRCSHIFT)
            y = str(CIRCSHIFT)
            rotZ = str(pSPhiVal + Val(width) * 180# / PI / 2#)
        Case "kPhi"
            x = str(CIRCSHIFT)
            y = str(CIRCSHIFT)
            rotZ = str(pSPhiVal + Val(width) * 180# / PI / 2#)
'-------------------------------------------------------------------------------------------------------------------------------------------
        Case Else
            MsgBox "Unknown axis found as a direction in replicate_along_axis: " & direction, vbCritical
    End Select

    Dim prt As Part
    Dim shpFactory As ShapeFactory
    Dim objToPat As Shape
    Dim bd As Body
    Dim Intersection_XY_ZX As HybridShapeIntersection
    Dim Intersection_YZ_XY As HybridShapeIntersection
    Dim Intersection_ZX_YZ As HybridShapeIntersection

    Set prt = Insert(childVolumeName, motherVolumeName, Val(x), Val(y), Val(z), 0, 0, -Val(rotZ), "mm", "deg")

    Set shpFactory = prt.ShapeFactory
    Set objToPat = prt.Bodies.Item(prt.Bodies.Count).Shapes.Item(prt.Bodies.Item(prt.Bodies.Count).Shapes.Count)
    Set bd = prt.Bodies.Item(prt.Bodies.Count)
    Set Intersection_XY_ZX = bd.HybridShapes.GetItem("X axis")
    Set Intersection_YZ_XY = bd.HybridShapes.GetItem("Y axis")
    Set Intersection_ZX_YZ = bd.HybridShapes.GetItem("Z axis")

    Dim createdPattern As Shape

' here are different shifts for visualising ------------------------------------------------------------------------------------------------
    Select Case direction
        Case "x"
            Set createdPattern = shpFactory.AddNewRectPattern(objToPat, Val(number), 1, Val(width) * unitConvert(wunit) + STEPADD, 10#, 1, 1, Intersection_XY_ZX, Intersection_YZ_XY, False, False, 0#)
            createdPattern.name = "Replica.X"
        Case "kXAxis"
            Set createdPattern = shpFactory.AddNewRectPattern(objToPat, Val(number), 1, Val(width) * unitConvert(wunit) + STEPADD, 10#, 1, 1, Intersection_XY_ZX, Intersection_YZ_XY, False, False, 0#)
            createdPattern.name = "Replica.X"
        Case "y"
            Set createdPattern = shpFactory.AddNewRectPattern(objToPat, Val(number), 1, Val(width) * unitConvert(wunit) + STEPADD, 10#, 1, 1, Intersection_YZ_XY, Intersection_ZX_YZ, False, False, 0#)
            createdPattern.name = "Replica.Y"
        Case "kYAxis"
            Set createdPattern = shpFactory.AddNewRectPattern(objToPat, Val(number), 1, Val(width) * unitConvert(wunit) + STEPADD, 10#, 1, 1, Intersection_YZ_XY, Intersection_ZX_YZ, False, False, 0#)
            createdPattern.name = "Replica.Y"
        Case "z"
            Set createdPattern = shpFactory.AddNewRectPattern(objToPat, Val(number), 1, Val(width) * unitConvert(wunit) + STEPADD, 10#, 1, 1, Intersection_ZX_YZ, Intersection_XY_ZX, False, False, 0#)
            createdPattern.name = "Replica.Z"
        Case "kZAxis"
            Set createdPattern = shpFactory.AddNewRectPattern(objToPat, Val(number), 1, Val(width) * unitConvert(wunit) + STEPADD, 10#, 1, 1, Intersection_ZX_YZ, Intersection_XY_ZX, False, False, 0#)
            createdPattern.name = "Replica.Z"
        Case "phi"
            If wunit = "mm" Then wunit = "radian" ' ???
            If ounit = "mm" Then ounit = "radian" ' ???
            Set createdPattern = shpFactory.AddNewCircPattern(objToPat, 1, Val(number), 10#, Val(width) * unitConvert(wunit) + CIRCSHIFT, 1, 1, Intersection_ZX_YZ, Intersection_ZX_YZ, True, Val(offset) * unitConvert(ounit), True)
            createdPattern.name = "Replica.P"
        Case "kPhi"
            If wunit = "mm" Then wunit = "radian" ' ???
            If ounit = "mm" Then ounit = "radian" ' ???
            Set createdPattern = shpFactory.AddNewCircPattern(objToPat, 1, Val(number), 10#, Val(width) * unitConvert(wunit) + CIRCSHIFT, 1, 1, Intersection_ZX_YZ, Intersection_ZX_YZ, True, Val(offset) * unitConvert(ounit), True)
            createdPattern.name = "Replica.P"
    End Select
'------------------------------------------------------------------------------------------------------------------------------------------

End Sub

Public Function nameGenerate(partDoc As PartDocument, base As String) As String

' TODO optimize
' instead of looping through the collection of bodies
' maybe it is better to keep the max index for each volume name

    Dim prefixLine As String
    Dim indexLine As String
    Dim i As Integer
    Dim maxIndex As Integer
    prefixLine = "Body." & base & "."
    maxIndex = 0
    For i = 1 To partDoc.Part.Bodies.Count
        If (StrComp(Mid(partDoc.Part.Bodies.Item(i).name, 1, Len(prefixLine)), prefixLine, vbTextCompare) = 0) Then
            indexLine = Mid(partDoc.Part.Bodies.Item(i).name, Len(prefixLine) + 1)
            If ((CommonDigitalString.isNum(indexLine) = True) And (Val(indexLine) > maxIndex)) Then
                maxIndex = Val(indexLine)
'            Else
'                MsgBox indexLine
            End If
        End If
    Next
    nameGenerate = prefixLine & (maxIndex + 1)

End Function

Public Sub ProcessBodyPosition(prt As Part, bd As Body, _
                        x As String, y As String, z As String, _
                        xr As String, yr As String, zr As String, _
                        lunit As String, aunit As String)

    timer.StartCounter

    Dim hybShpFactory As HybridShapeFactory
    Dim shpFactory As ShapeFactory
    Dim origin As OriginElements
    Dim refPlaneXY As Reference
    Dim refPlaneYZ As Reference
    Dim refPlaneZX As Reference
    Dim sel As Selection
    Dim visPropSet As VisPropertySet

    Set hybShpFactory = prt.HybridShapeFactory
    Set shpFactory = prt.ShapeFactory
    Set origin = prt.OriginElements
    Set refPlaneXY = prt.CreateReferenceFromObject(origin.PlaneXY)
    Set refPlaneYZ = prt.CreateReferenceFromObject(origin.PlaneYZ)
    Set refPlaneZX = prt.CreateReferenceFromObject(origin.PlaneZX)
    Set sel = CATIA.ActiveDocument.Selection
    Set visPropSet = sel.VisProperties

    Dim Intersection_XY_ZX As HybridShapeIntersection
    Dim Intersection_YZ_XY As HybridShapeIntersection
    Dim Intersection_ZX_YZ As HybridShapeIntersection

    'Z axis preparation
    Set Intersection_ZX_YZ = hybShpFactory.AddNewIntersection(refPlaneZX, refPlaneYZ)
    Intersection_ZX_YZ.PointType = 0
    bd.InsertHybridShape Intersection_ZX_YZ
'    prt.InWorkObject = Intersection_ZX_YZ
    Intersection_ZX_YZ.name = "Z axis"
    sel.Clear
    sel.Add Intersection_ZX_YZ
    visPropSet.SetShow catVisPropertyNoShowAttr
    sel.Clear
'    prt.Update
    'Y axis preparation
    Set Intersection_YZ_XY = hybShpFactory.AddNewIntersection(refPlaneYZ, refPlaneXY)
    Intersection_YZ_XY.PointType = 0
    bd.InsertHybridShape Intersection_YZ_XY
'    prt.InWorkObject = Intersection_YZ_XY
    Intersection_YZ_XY.name = "Y axis"
    sel.Clear
    sel.Add Intersection_YZ_XY
    visPropSet.SetShow catVisPropertyNoShowAttr
    sel.Clear
'    prt.Update
    'X axis preparation
    Set Intersection_XY_ZX = hybShpFactory.AddNewIntersection(refPlaneXY, refPlaneZX)
    Intersection_XY_ZX.PointType = 0
    bd.InsertHybridShape Intersection_XY_ZX
'    prt.InWorkObject = Intersection_XY_ZX
    Intersection_XY_ZX.name = "X axis"
    sel.Clear
    sel.Add Intersection_XY_ZX
    visPropSet.SetShow catVisPropertyNoShowAttr
    sel.Clear
'    prt.Update

    formProfiling.ListBox1.AddItem timer.TimeElapsed
    timer.StartCounter

    Dim refAxisX As Reference
    Dim refAxisY As Reference
    Dim refAxisZ As Reference
    Dim hybShpRotX As HybridShapeRotate
    Dim hybShpRotY As HybridShapeRotate
    Dim hybShpRotZ As HybridShapeRotate
    Dim hybShpTrans As HybridShapeTranslate
    Dim rotX As Rotate
    Dim rotY As Rotate
    Dim rotZ As Rotate
    Dim trans As Translate

    'Rotate by Z axis creation
    Set refAxisZ = prt.CreateReferenceFromObject(Intersection_ZX_YZ)
    Set rotZ = shpFactory.AddNewRotate2(refAxisZ, -Val(Replace(zr, ",", ".")) * unitConvert(aunit))
    Set hybShpRotZ = rotZ.HybridShape
    hybShpRotZ.RotationType = 0
    hybShpRotZ.axis = refAxisZ
    hybShpRotZ.name = "Rotate.Z"
'    prt.InWorkObject = hybShpRotZ
'    prt.Update
    'Rotate by Y axis creation
    Set refAxisY = prt.CreateReferenceFromObject(Intersection_YZ_XY)
    Set rotY = shpFactory.AddNewRotate2(refAxisY, -Val(Replace(yr, ",", ".")) * unitConvert(aunit))
    Set hybShpRotY = rotY.HybridShape
    hybShpRotY.RotationType = 0
    hybShpRotY.axis = refAxisY
    hybShpRotY.name = "Rotate.Y"
'    prt.InWorkObject = hybShpRotY
'    prt.Update
    'Rotate by X axis creation
    Set refAxisX = prt.CreateReferenceFromObject(Intersection_XY_ZX)
    Set rotX = shpFactory.AddNewRotate2(refAxisX, -Val(Replace(xr, ",", ".")) * unitConvert(aunit))
    Set hybShpRotX = rotX.HybridShape
    hybShpRotX.RotationType = 0
    hybShpRotX.axis = refAxisX
    hybShpRotX.name = "Rotate.X"
'    prt.InWorkObject = hybShpRotX
'    prt.Update

    formProfiling.ListBox2.AddItem timer.TimeElapsed
    timer.StartCounter

    'Translation
    Set trans = shpFactory.AddNewTranslate2(0)
    Set hybShpTrans = trans.HybridShape
    hybShpTrans.VectorType = 2
    hybShpTrans.CoordXValue = Val(x) * unitConvert(lunit) / 1000#
    hybShpTrans.CoordYValue = Val(y) * unitConvert(lunit) / 1000#
    hybShpTrans.CoordZValue = Val(z) * unitConvert(lunit) / 1000#
'    prt.InWorkObject = hybShpTrans

    formProfiling.ListBox3.AddItem timer.TimeElapsed
    timer.StartCounter

    ' Parameterization ?
    Dim prodDoc As ProductDocument
    Set prodDoc = CATIA.ActiveDocument
    Dim prod As Product
    Set prod = prodDoc.Product
    Dim rels As Relations
    Set rels = prod.Relations
    Dim params As Parameters
    Set params = prod.Parameters

    CreateFormula prt, zr, rotZ.angle, rels, "_rotZ"
    CreateFormula prt, yr, rotY.angle, rels, "_rotY"
    CreateFormula prt, xr, rotX.angle, rels, "_rotZ"
    
    Dim transNr As Integer
    'transNr = getTransNr(prt)
    Dim shps As Shapes
    Set shps = bd.Shapes
    Dim shpName As String
    shpName = shps.Item(shps.Count).name
    
    ' fckng optimization
    CreateFormula2 prt, z, prt.name & "\" & bd.name & "\" & shpName & "\CoordZ", rels, "_z", params
    CreateFormula2 prt, y, prt.name & "\" & bd.name & "\" & shpName & "\CoordY", rels, "_y", params
    CreateFormula2 prt, x, prt.name & "\" & bd.name & "\" & shpName & "\CoordX", rels, "_x", params

    formProfiling.ListBox4.AddItem timer.TimeElapsed

End Sub

Public Sub TagsCheck(GDML As DOMDocument60, startTag As IXMLDOMNode)

    Dim i As Integer

    If startTag.childNodes.Length > 0 Then
        For i = 0 To startTag.childNodes.Length - 1
            TagsCheck GDML, startTag.childNodes.Item(i)
        Next i
    End If

'    If TagSupported(startTag.nodeName) = False Then _
'        MsgBox "Tag not supported." & Chr(13) & startTag.nodeName

End Sub

Public Function TagSupported(name As String) As Boolean

    If name = "gdml" Or _
        name = "define" Or name = "materials" Or name = "solids" Or name = "structure" Or name = "setup" Or _
        name = "position" Or name = "rotation" Or name = "positionref" Or name = "rotationref" Or _
        name = "material" Or name = "D" Or name = "atom" Or name = "fraction" Or _
        name = "T" Or name = "P" Or _
 _
        name = "arb8" Or name = "box" Or name = "cone" Or name = "ellipsoid" Or _
        name = "elcone" Or name = "eltube" Or name = "orb" Or _
        name = "para" Or name = "sphere" Or name = "torus" Or _
        name = "trap" Or name = "trd" Or name = "tube" Or _
        name = "twistedbox" Or name = "twistedtrap" Or _
        name = "twistedtrd" Or name = "twistedtubs" Or _
        name = "xtru" Or name = "twoDimVertex" Or name = "section" Or _
        name = "polycone" Or name = "polyhedra" Or name = "zplane" Or name = "hedra" Or _
 _
        name = "union" Or name = "subtraction" Or name = "intersection" Or name = "first" Or name = "second" Or _
        name = "volume" Or name = "materialref" Or name = "solidref" Or name = "physvol" Or name = "volumeref" Or _
        name = "replicavol" Or name = "divisionvol" Or name = "replicate_along_axis" Or name = "direction" Or _
        name = "width" Or name = "offset" Or name = "world" Then
            TagSupported = True
    Else
            TagSupported = False
    End If

End Function

Public Sub CreateParameters(GDML As DOMDocument60)

    Dim params As Parameters
    Set params = CATIA.ActiveDocument.Product.Parameters

    Dim rels As Relations
    Set rels = CATIA.ActiveDocument.Product.Relations

    Dim vars As IXMLDOMNodeList
    Set vars = GDML.getElementsByTagName("variable")

    Dim paramStr As String
    Dim len1 As Length
    Dim ang1 As angle
    Dim real1 As RealParam
    Dim formula1 As Formula
    Dim i As Integer

    Dim curParamName As String

    For i = 0 To vars.Length - 1

        curParamName = vars.Item(i).Attributes.getNamedItem("name").Text

        formGDML2CATIA.lblStatus.Caption = "Step 1/4. Creating parameter " + curParamName + _
                vbNewLine + str(i + 1) + "/" + Trim(str(vars.Length))
                
        ' value or formula
        paramStr = Replace(vars.Item(i).Attributes.getNamedItem("value").nodeValue, ",", ".")
        
        If (IsNumeric(paramStr)) Then
            ' value
            Set real1 = params.CreateReal(curParamName, Val(paramStr))
        Else
            ' formula
            Set real1 = params.CreateReal(curParamName, 0#)
            Set formula1 = rels.CreateFormula("Formula." + curParamName, "", real1, paramStr)
        End If
        
'        If (InStr(1, paramStr, "mm") <> 0) Then
'            Set len1 = params.CreateDimension("", "LENGTH", 0#)
'            len1.Rename curParamName
'            len1.ValuateFromString (str(Val(paramStr) * unitConvert("mm")) & "mm")
'        ElseIf (InStr(1, paramStr, "deg") <> 0) Then
'            Set ang1 = params.CreateDimension("", "ANGLE", 0#)
'            ang1.Rename curParamName
'            ang1.ValuateFromString (str(Val(paramStr) * unitConvert("deg")) & "deg")
'        Else
'            Set real1 = params.CreateReal(curParamName, Val(paramStr))
'        End If

    Next i

End Sub

' Useless staff
'Public Function getTransNr(prt As Part) As Integer
'
'    Dim params As Parameters
'    Set params = prt.Parameters
'    Dim i As Integer
'    Dim nr As Integer
'    nr = 0
'    For i = 1 To params.Count
'        If (InStr(1, params.Item(i).name, "Translate")) Then
'            nr = nr + 1
'        End If
'    Next i
'    getTransNr = nr / 5           ' magic?
'    If getTransNr = 0 Then
'        getTransNr = 1
'    End If
'
'End Function

' Useless staff
'Public Function getAddNr(prt As Part) As Integer
'
'    Dim i As Integer
'    Dim nr As Integer
'    Dim params As Parameters
'    Set params = prt.Parameters
'    For i = 1 To params.Count
'        If (InStr(1, params.Item(i).name, "Add")) Then
'            nr = nr + 1
'        End If
'    Next i
'    getAddNr = nr
'
'End Function

Attribute VB_Name = "formGDML2CATIA"
Attribute VB_Base = "0{FC332AC6-260D-402A-9AF8-4CEBEF5C17E9}{0485CECE-4E28-40B8-A479-7320AFBF0F71}"
Attribute VB_GlobalNameSpace = False
Attribute VB_Creatable = False
Attribute VB_PredeclaredId = True
Attribute VB_Exposed = False
Attribute VB_TemplateDerived = False
Attribute VB_Customizable = False
Option Explicit

Private Sub UserForm_Click()

    ' Profiling
    formProfiling.Show vbModeless

End Sub

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument

    ' Translate to design mode
'    MsgBox "Parts in this product are to be translated into 'Design Mode'" + vbNewLine + "This may take a few minutes, please wait.", vbExclamation, "Translate to Design mode"
'    prodDoc.Product.ApplyWorkMode DESIGN_MODE

End Sub

Private Sub cmbGDML_Click()

    cdcGDML.Filter = "GDML files (*.gdml)|*.gdml|XML files (*.xml)|*.xml|All files (*.*)|*.*"
    cdcGDML.ShowOpen
    If (cdcGDML.FileName = "" And txtGDML.Text = "") Then
        MsgBox "Invalid file name", vbCritical, "Error"
        Exit Sub
    ElseIf cdcGDML.FileName = "" Then
        Exit Sub
    End If
    txtGDML.Text = cdcGDML.FileName

End Sub

Private Sub cmbStart_Click()

    Dim prodDoc As ProductDocument
    Dim prod As Product
    Dim elemDir As String
    Dim gdmlFile As String
    Dim GDML As DOMDocument60

    Set prodDoc = CATIA.ActiveDocument
    Set prod = prodDoc.Product
    Set GDML = New DOMDocument60

    If txtGDML.Text = "" Then
        MsgBox "Please specify GDML file to import", vbExclamation, "Incorrect input file"
        Exit Sub
    Else
        gdmlFile = txtGDML.Text
    End If

    elemDir = CATIA.SystemService.Environ("BuilderPath") + "\02_Elements"

    If GDML.Load(gdmlFile) = False Then
        MsgBox "Failed to open the file. Please specify correct GDML file.", vbCritical, "Error"
        Exit Sub
    End If

    ' Initialize regular expressions
    Call InitRegexp

    TagsCheck GDML, GDML.getElementsByTagName("gdml").Item(0)

    CreateParameters GDML
    CreateGeometry GDML, elemDir
    prod.Update
    ProcessInserting GDML
    prod.Update
    ProcessMaterials GDML

    MsgBox "Conversion successfully completed!", vbOKOnly Or vbExclamation, "GDML2CATIA"

    prod.Update

End Sub

Private Sub cmbExit_Click()

    End

End Sub
