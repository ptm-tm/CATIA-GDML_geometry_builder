Attribute VB_Name = "Measure"
Sub CATMain()

    formMeasure.Show vbModeless

End Sub

Attribute VB_Name = "formMeasure"
Attribute VB_Base = "0{60E84688-E258-4191-900A-BD9AD28E7ED7}{2892776C-F3B5-4960-B0F0-6C3019C54ECE}"
Attribute VB_GlobalNameSpace = False
Attribute VB_Creatable = False
Attribute VB_PredeclaredId = True
Attribute VB_Exposed = False
Attribute VB_TemplateDerived = False
Attribute VB_Customizable = False
Option Explicit

Dim AFormMethodIsBeingExecuted As Boolean
Dim stat

Private Sub tbMesBetw_Change()
    If tbMesBetw.Value = True Then
        tbMesItem.Value = False
    Else
        tbMesItem.Value = True
    End If
End Sub

Private Sub tbMesItem_Change()
    If tbMesItem.Value = True Then
        tbMesBetw.Value = False
    Else
        tbMesBetw.Value = True
    End If
End Sub

Private Sub UserForm_Initialize()

    Dim prtDoc  As PartDocument
    Dim prodDoc As ProductDocument
    Dim prt As Part
    Dim params As Parameters
    Dim param As Parameter
    Dim sel As Selection

    ' Get the parameters collection according to the filetype
    If TypeName(CATIA.ActiveDocument) = "PartDocument" Then
        Set prtDoc = CATIA.ActiveDocument
        Set prt = prtDoc.Part
        Set params = prt.Parameters
        Set sel = prtDoc.Selection
    ElseIf TypeName(CATIA.ActiveDocument) = "ProductDocument" Then
        Set prodDoc = CATIA.ActiveDocument
        Set params = prodDoc.Product.Parameters
        Set sel = prodDoc.Selection
    Else
        MsgBox "The type of the active document must be a product or a part", vbCritical, "Incorrect active document type"
        End
    End If

    Dim selProd As Product

    If sel.Count > 0 Then
        Set selProd = sel.Item(1).LeafProduct
        Set params = selProd.Parameters
    End If

    ' Parse the parameters collection and put the data into the tree
    ParseParamsToTree params

    Dim i As Integer
    ' Expand all levels
    For i = 1 To treeParams.Nodes.Count
        treeParams.Nodes.Item(i).Expanded = True
    Next i

    If sel.Count = 0 Then
        ' Collapse 2nd level
        Dim nodx As Node
        Set nodx = treeParams.Nodes("root").Child
        For i = 1 To treeParams.Nodes("root").Children
             nodx.Expanded = False
             Set nodx = nodx.Next
        Next i
    End If

    ' Fill the list (invisible)
    For i = 1 To params.Count
        Set param = params.Item(i)
        lstParams.AddItem param.name
    Next i

    ' GUI
    lblStatus.Caption = "Press 'Measure' button."

End Sub

Private Sub cmbMeasure_Click()

    Dim prtDoc As PartDocument
    Dim prodDoc As ProductDocument
    Dim sel
    Dim inpObjType(0)
    Dim inpObjType2(1)
    Dim lin
    Dim lin1
    Dim lin2
    Dim hybShpRef1 As Reference
    Dim hybShpRef2 As Reference
    Dim length(3) As Double
    Dim TheSPAWorkbench As Workbench
    Dim Measure ' As Measurable
    Dim Measure1 ' As Measurable
    Dim Measure2 ' As Measurable
    Dim i As Integer

    If TypeName(CATIA.ActiveDocument) = "PartDocument" Then
        Set prtDoc = CATIA.ActiveDocument
        Set sel = prtDoc.Selection
        Set TheSPAWorkbench = prtDoc.GetWorkbench("SPAWorkbench")
    ElseIf TypeName(CATIA.ActiveDocument) = "ProductDocument" Then
        Set prodDoc = CATIA.ActiveDocument
        Set sel = prodDoc.Selection
        Set TheSPAWorkbench = prodDoc.GetWorkbench("SPAWorkbench")
    End If

    If tbMesItem.Value = True Then      ' Mesure item
        inpObjType(0) = "MonoDim"
    
        lblStatus.Caption = "Choose the geometric element (edge) in the geometry area."
        AFormMethodIsBeingExecuted = True
        stat = sel.SelectElement2(inpObjType, "Select an edge", False)
        AFormMethodIsBeingExecuted = False
        lblStatus.Caption = "Choose the parameter in the list and press 'Apply' button."
    
        If (stat = "Normal") Then
            Set lin = sel.Item2(1)
            Set hybShpRef1 = lin.Reference
            Set Measure = TheSPAWorkbench.GetMeasurable(hybShpRef1)
            length(1) = Measure.length
            txtL.Text = length(1)
            txtR.Text = ""
On Error GoTo 23
            length(2) = Measure.Radius
            txtR.Text = length(2)
23
        Else
            End
        End If
    Else                                ' Measure between
        inpObjType2(0) = "Vertex"
        inpObjType2(1) = "MonoDim"
    
        lblStatus.Caption = "Choose the first geometric element (point) in the geometry area."
        AFormMethodIsBeingExecuted = True
        stat = sel.SelectElement2(inpObjType2, "Select a vertex", False)
        AFormMethodIsBeingExecuted = False
    
        If (stat = "Normal") Then
            Set lin1 = sel.Item2(1)
            Set hybShpRef1 = lin1.Reference
            Set Measure1 = TheSPAWorkbench.GetMeasurable(hybShpRef1)
        Else
            End
        End If
    
        lblStatus.Caption = "Choose the second geometric element (point) in the geometry area."
        AFormMethodIsBeingExecuted = True
        stat = sel.SelectElement2(inpObjType2, "Select a vertex", False)
        AFormMethodIsBeingExecuted = False
    
        If (stat = "Normal") Then
            Set lin2 = sel.Item2(1)
            Set hybShpRef2 = lin2.Reference
            Set Measure2 = TheSPAWorkbench.GetMeasurable(hybShpRef2)
        Else
            End
        End If

        txtL.Text = Measure2.GetMinimumDistance(hybShpRef1)
        txtR.Text = ""

    End If

End Sub

Private Sub cmbApply_Click()

    Dim prtDoc As PartDocument
    Dim prodDoc As ProductDocument
    Dim prt As Part
    Dim prod As Product
    Dim params As Parameters
    Dim param As Parameter

    If TypeName(CATIA.ActiveDocument) = "PartDocument" Then
        Set prtDoc = CATIA.ActiveDocument
        Set prt = prtDoc.Part
        Set params = prt.Parameters
    ElseIf TypeName(CATIA.ActiveDocument) = "ProductDocument" Then
        Set prodDoc = CATIA.ActiveDocument
        Set prod = prodDoc.Product
        Set params = prod.Parameters
    End If

    Set param = params.GetItem(Mid(treeParams.SelectedItem.Key, 6))

    Dim Valu As Double
    If chkDiv.Value = True Then
        If (optL.Value = True) Then
            Valu = val(txtL.Text) / 2#
        Else
            Valu = val(txtR.Text) / 2#
        End If
    Else
        If (optL.Value = True) Then
            Valu = val(txtL.Text)
        Else
            Valu = val(txtR.Text)
        End If
    End If
    param.ValuateFromString (Valu & "mm")

    ' GUI
    lblStatus.Caption = "Press 'Measure' button."

    If TypeName(CATIA.ActiveDocument) = "PartDocument" Then
        prt.Update
    ElseIf TypeName(CATIA.ActiveDocument) = "ProductDocument" Then
        prod.Update
    End If

End Sub

Private Sub cmbExit_Click()

    End

End Sub

Private Sub ParseParamsToTree(params As Parameters)

    Dim i As Integer
    Dim j As Integer
    Dim TailString As String
    Dim CurrentString As String
    Dim Valu As String
    Dim curKey As String
    Dim branchFound As Boolean
    Dim keyAlreadyExists As Boolean
    Dim postfix As Integer
    postfix = 2

    Dim SeparatorPosition As Integer

    treeParams.Nodes.Add , , "root", "root"
    
    For i = 1 To params.Count
        TailString = params.Item(i).name
        Valu = params.Item(i).ValueAsString

        curKey = "root"
        Do While (Len(TailString) > 0)
            SeparatorPosition = InStr(1, TailString, "\", vbTextCompare)
            If (SeparatorPosition > 0) Then

                ' Current branch or leaf name
                CurrentString = Left(TailString, SeparatorPosition - 1)

                ' Skip Constraints
                If CurrentString = "Constraints" Then GoTo NextParam

                ' Skip Axes
                If CurrentString = "X axis" Or _
                    CurrentString = "Y axis" Or _
                    CurrentString = "Z axis" Then GoTo NextParam

                ' Deeper
                TailString = Mid(TailString, SeparatorPosition + 1)

                ' Look for the current branch in the existing tree
                ' If not found - create this branch
                branchFound = False
                For j = 1 To treeParams.Nodes.Count
                    If treeParams.Nodes.Item(j).Key = curKey & "\" & CurrentString Then
                        branchFound = True
                        Exit For
                    End If
                Next j
                If (branchFound = False) Then
                    treeParams.Nodes.Add curKey, tvwChild, curKey & "\" & CurrentString, CurrentString
                End If
                curKey = curKey & "\" & CurrentString
            Else
                CurrentString = TailString
                TailString = ""
                ' From here we naturally exit from the loop (condition not satisfied on the next iteration)
                ' This means that the leaf has been found
            End If
        Loop

        keyAlreadyExists = False
        For j = 1 To treeParams.Nodes.Count
            If treeParams.Nodes.Item(j).Key = curKey & "\" & CurrentString Then
                keyAlreadyExists = True
                Exit For
            End If
        Next j

        If Not ToBeIgnored(CurrentString) Then
            If keyAlreadyExists = False Then
                treeParams.Nodes.Add curKey, tvwChild, curKey & "\" & CurrentString, CurrentString & " = " & Valu
            Else
                treeParams.Nodes.Add curKey, tvwChild, curKey & "\" & CurrentString & Str(postfix), CurrentString & " = " & Valu
                postfix = postfix + 1
            End If

        End If

NextParam:

    Next i

End Sub

Private Function ToBeIgnored(name As String) As Boolean

    ToBeIgnored = False

    If name = "Activity" Then ToBeIgnored = True
    If name = "Mode" Then ToBeIgnored = True
    If name = "Nomenclature" Then ToBeIgnored = True
    If name = "Revision" Then ToBeIgnored = True
    If name = "Product Description" Then ToBeIgnored = True
    If name = "Definition" Then ToBeIgnored = True
    If name = "Component Activation State" Then ToBeIgnored = True

' Uncomment this if you want to keep the materials in the list
    If name = "Material" Then ToBeIgnored = True

End Function

Private Sub treeParams_Click()

    lblSelectedKey.Caption = treeParams.SelectedItem.Key

End Sub

' В CATIA есть глюк - в дереве параметров встречаются одинаковые элементы.
' Чтобы не заморачиваться с правильной обработкой таких параметров делается так:
' если встретился параметр, ключ которого совпадает с каким-то из предыдущих,
' генерируется новый ключ дописыванием индекса в конце.
' Проблема лишь в том, что в момент обращения к параметру c попыткой изменить значение
' используется ключ. Если этот ключ имеет дописанный индекс, то будет ошибка, потому
' как такого параметра не существует.
