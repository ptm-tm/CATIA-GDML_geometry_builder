Attribute VB_Name = "CommonDigitalString"
Option Explicit

Public Function unitConvert(unit As String) As Double

    Dim PI As Double
    PI = 3.14159265358979
    Select Case unit
        Case "mm"
            unitConvert = 1#
        Case "cm"
            unitConvert = 10#
        Case "m"
            unitConvert = 1000#
        Case "deg"
            unitConvert = 1#
        Case "degree"
            unitConvert = 1#
        Case "radian"
            unitConvert = 180# / PI
    End Select

End Function

Public Function isNum(str As String) As Boolean

    Dim i As Integer
    Dim flag As Boolean
    flag = False
    isNum = True
    For i = 1 To Len(str)
        If isDigit(Mid(str, i, 1)) = False Then
            isNum = False
        End If
    Next

End Function

Public Function isDigit(str As String) As Boolean

    Dim arr(0 To 9) As String
    Dim i As Integer
    arr(0) = "0"
    arr(1) = "1"
    arr(2) = "2"
    arr(3) = "3"
    arr(4) = "4"
    arr(5) = "5"
    arr(6) = "6"
    arr(7) = "7"
    arr(8) = "8"
    arr(9) = "9"
    isDigit = False
    For i = 0 To 9
        If str = arr(i) Then
            isDigit = True
        End If
    Next

End Function

Attribute VB_Name = "Inserter_sub_module"
Option Explicit

Function Insert(childVolumeName As String, _
            motherVolumeName As String, _
            x As String, y As String, z As String, _
            xr As String, yr As String, zr As String, _
            lunit As String, aunit As String) As Part

    Dim i As Integer
    Dim ProductDoc As ProductDocument
    Dim partDoc As PartDocument
    Dim docs As Documents
    Dim pub As Publication
    Dim sel As Selection
    
    Set sel = CATIA.ActiveDocument.Selection
    Set ProductDoc = CATIA.ActiveDocument
    Set docs = CATIA.Documents
    
    'coincidence_std_planes         ' is it needed here?
    
    For i = 1 To ProductDoc.Product.Products.Count
        If (ProductDoc.Product.Products.Item(i).PartNumber = childVolumeName) Then
            Set pub = ProductDoc.Product.Products.Item(i).Publications.Item("PartBody")
            Exit For
        End If
    Next
    
    For i = 1 To docs.Count
        If (Right(docs.Item(i).Name, 8) = ".CATPart") Then
            If (docs.Item(i).Product.PartNumber = motherVolumeName) Then
                Set partDoc = docs.Item(i)
                Exit For
            End If
        End If
    Next
    
    'copy - paste - as result with link
    sel.Clear
    sel.Add pub
    sel.Copy
    sel.Clear
    sel.Add partDoc.Part
    sel.PasteSpecial "CATPrtResult"
    sel.Clear
    
    'rename recent copied body
    partDoc.Part.Bodies.Item(partDoc.Part.Bodies.Count).Name = nameGenerate(partDoc, childVolumeName)
    
    'position
    ProcessBodyPosition partDoc.Part, partDoc.Part.Bodies.Item(partDoc.Part.Bodies.Count), x, y, z, xr, yr, zr, lunit, aunit
    
    Set Insert = partDoc.Part

End Function

Sub ProcessBodyPosition(prt As Part, bd As Body, _
                        x As String, y As String, z As String, _
                        xr As String, yr As String, zr As String, _
                        lunit As String, aunit As String)

    Dim hybShpFactory As HybridShapeFactory
    Dim shpFactory As ShapeFactory
    Dim origin As OriginElements
    Dim hybShpRotX As HybridShapeRotate
    Dim hybShpRotY As HybridShapeRotate
    Dim hybShpRotZ As HybridShapeRotate
    Dim hybShpTrans As HybridShapeTranslate
    Dim rotX As Rotate
    Dim rotY As Rotate
    Dim rotZ As Rotate
    Dim trans As Translate
    Dim sel As Selection
    Dim visPropSet As VisPropertySet
    Dim refAxisX As Reference
    Dim refAxisY As Reference
    Dim refAxisZ As Reference
    Dim refPlaneXY As Reference
    Dim refPlaneYZ As Reference
    Dim refPlaneZX As Reference
    Dim Intersection_XY_ZX As HybridShapeIntersection
    Dim Intersection_YZ_XY As HybridShapeIntersection
    Dim Intersection_ZX_YZ As HybridShapeIntersection
    
    Set hybShpFactory = prt.HybridShapeFactory
    Set shpFactory = prt.ShapeFactory
    Set origin = prt.OriginElements
    Set refPlaneXY = prt.CreateReferenceFromObject(origin.PlaneXY)
    Set refPlaneYZ = prt.CreateReferenceFromObject(origin.PlaneYZ)
    Set refPlaneZX = prt.CreateReferenceFromObject(origin.PlaneZX)
    Set sel = CATIA.ActiveDocument.Selection
    Set visPropSet = sel.VisProperties
    
    'Z axis preparation
    Set Intersection_ZX_YZ = hybShpFactory.AddNewIntersection(refPlaneZX, refPlaneYZ)
    Intersection_ZX_YZ.PointType = 0
    bd.InsertHybridShape Intersection_ZX_YZ
    prt.InWorkObject = Intersection_ZX_YZ
    Intersection_ZX_YZ.Name = "Z axis"
    sel.Clear
    sel.Add Intersection_ZX_YZ
    visPropSet.SetShow catVisPropertyNoShowAttr
    sel.Clear
    prt.Update
    'Y axis preparation
    Set Intersection_YZ_XY = hybShpFactory.AddNewIntersection(refPlaneYZ, refPlaneXY)
    Intersection_YZ_XY.PointType = 0
    bd.InsertHybridShape Intersection_YZ_XY
    prt.InWorkObject = Intersection_YZ_XY
    Intersection_YZ_XY.Name = "Y axis"
    sel.Clear
    sel.Add Intersection_YZ_XY
    visPropSet.SetShow catVisPropertyNoShowAttr
    sel.Clear
    prt.Update
    'X axis preparation
    Set Intersection_XY_ZX = hybShpFactory.AddNewIntersection(refPlaneXY, refPlaneZX)
    Intersection_XY_ZX.PointType = 0
    bd.InsertHybridShape Intersection_XY_ZX
    prt.InWorkObject = Intersection_XY_ZX
    Intersection_XY_ZX.Name = "X axis"
    sel.Clear
    sel.Add Intersection_XY_ZX
    visPropSet.SetShow catVisPropertyNoShowAttr
    sel.Clear
    prt.Update
    
    'Rotate by Z axis creation
    Set refAxisZ = prt.CreateReferenceFromObject(Intersection_ZX_YZ)
    Set rotZ = shpFactory.AddNewRotate2(refAxisZ, Val(zr) * unitConvert(aunit))
    Set hybShpRotZ = rotZ.HybridShape
    hybShpRotZ.RotationType = 0
    hybShpRotZ.Axis = refAxisZ
    hybShpRotZ.Name = "Rotate.Z"
    prt.InWorkObject = hybShpRotZ
    prt.Update
    'Rotate by Y axis creation
    Set refAxisY = prt.CreateReferenceFromObject(Intersection_YZ_XY)
    Set rotY = shpFactory.AddNewRotate2(refAxisY, Val(yr) * unitConvert(aunit))
    Set hybShpRotY = rotY.HybridShape
    hybShpRotY.RotationType = 0
    hybShpRotY.Axis = refAxisY
    hybShpRotY.Name = "Rotate.Y"
    prt.InWorkObject = hybShpRotY
    prt.Update
    'Rotate by X axis creation
    Set refAxisX = prt.CreateReferenceFromObject(Intersection_XY_ZX)
    Set rotX = shpFactory.AddNewRotate2(refAxisX, Val(xr) * unitConvert(aunit))
    Set hybShpRotX = rotX.HybridShape
    hybShpRotX.RotationType = 0
    hybShpRotX.Axis = refAxisX
    hybShpRotX.Name = "Rotate.X"
    prt.InWorkObject = hybShpRotX
    prt.Update
    
    'Translation
    Set trans = shpFactory.AddNewTranslate2(0)
    Set hybShpTrans = trans.HybridShape
    hybShpTrans.VectorType = 2
    hybShpTrans.CoordXValue = Val(x) * unitConvert(lunit) / 1000#
    hybShpTrans.CoordYValue = Val(y) * unitConvert(lunit) / 1000#
    hybShpTrans.CoordZValue = Val(z) * unitConvert(lunit) / 1000#
    prt.InWorkObject = hybShpTrans
    prt.Update

End Sub

Function nameGenerate(partDoc As PartDocument, base As String) As String

    Dim prefixLine As String
    Dim indexLine As String
    Dim i As Integer
    Dim maxIndex As Integer
    prefixLine = "Body." & base & "."
    maxIndex = 0
    For i = 1 To partDoc.Part.Bodies.Count
        If (StrComp(Mid(partDoc.Part.Bodies.Item(i).Name, 1, Len(prefixLine)), prefixLine, vbTextCompare) = 0) Then
            indexLine = Mid(partDoc.Part.Bodies.Item(i).Name, Len(prefixLine) + 1)
            If ((isNum(indexLine) = True) And (Val(indexLine) > maxIndex)) Then
                maxIndex = Val(indexLine)
            End If
        End If
    Next
    nameGenerate = prefixLine & (maxIndex + 1)

End Function

Attribute VB_Name = "Symmetry_noCopy"
Sub CATMain()

    formSymmetry_noCopy.Show

End Sub

Attribute VB_Name = "formSymmetry_noCopy"
Attribute VB_Base = "0{FF2803A5-42D4-45AD-9DD9-E13918071B7E}{A9884688-843A-4EDB-81BA-3AB95871C7E4}"
Attribute VB_GlobalNameSpace = False
Attribute VB_Creatable = False
Attribute VB_PredeclaredId = True
Attribute VB_Exposed = False
Attribute VB_TemplateDerived = False
Attribute VB_Customizable = False
Option Explicit

Const PI = 3.14159265358979

Private Sub UserForm_Initialize()

    Dim activeDoc As Document
    Set activeDoc = CATIA.ActiveDocument

    'Is active document a product?
    If Right(activeDoc.Name, 11) <> ".CATProduct" Then
        MsgBox "The type of the active document must be a product", vbCritical, "Incorrect active document type"
        End
    End If

End Sub

Private Sub cmbList_Click()

    Dim prodDoc As ProductDocument
    Dim prod As Product
    Dim subProds As Products
    Dim i As Integer
    
    Set prodDoc = CATIA.ActiveDocument
    Set prod = prodDoc.Product
    Set subProds = prod.Products

    For i = 1 To subProds.Count
        ListBox1.AddItem subProds.Item(i).Name
        ComboBox1.AddItem subProds.Item(i).Name
    Next i

    ComboBox1.Text = ComboBox1.List(ComboBox1.ListCount - 1)
    
End Sub

Private Sub cmbStart_Click()

    Dim prodDoc As ProductDocument
    Dim docs As Documents
    Dim prod As Product
    Dim subProds As Products
    Dim motherProd As Product
    Dim motherPart As Part
    Dim motherBodies As Bodies
    Dim bd As Body
    Dim shps As Shapes
    
    Dim rotZ As HybridShapeRotate
    Dim rotY As HybridShapeRotate
    Dim rotX As HybridShapeRotate
    Dim tr As HybridShapeTranslate

    Dim oldProd As Product
    Dim oldName As String
    Dim oldPartNum As String

    Set prodDoc = CATIA.ActiveDocument
    Set docs = CATIA.Documents
    Set prod = prodDoc.Product
    Set subProds = prod.Products
    Set motherProd = subProds.GetItem(ComboBox1.Text)

    For i = 1 To docs.Count
        If docs.Item(i).Name = (motherProd.PartNumber + ".CATPart") Then
            Set motherPartDoc = docs.Item(i)
            Exit For
        End If
    Next i
    
    Set motherPart = motherPartDoc.Part
    Set motherBodies = motherPart.Bodies

    For i = 0 To ListBox1.ListCount - 1
        If ListBox1.Selected(i) = True Then

            Set oldProd = subProds.GetItem(ListBox1.List(i))
            oldName = oldProd.Name
            oldPartNum = oldProd.PartNumber

            For j = 1 To motherBodies.Count
                If (InStr(motherBodies.Item(j).Name, oldPartNum) > 0) Then
                    ListBox2.AddItem motherBodies.Item(j).Name + " - " + oldPartNum
                    ' Нашли старое вхождение, можем узнать его параметры
                    Set bd = motherBodies.Item(j)
                    Set shps = bd.HybridShapes

                    Set rotZ = shps.GetItem("Rotate.Z")
                    Set rotY = shps.GetItem("Rotate.Y")
                    Set rotX = shps.GetItem("Rotate.X")

                    For k = 1 To bd.Shapes.Count
                        If InStr(bd.Shapes.Item(k).Name, "Translate.") > 0 Then
                            Set tr = bd.Shapes.Item(k)
                            Exit For
                        End If
                    Next k

                    ListBox2.AddItem str(tr.CoordXValue * 1000#) + "   " + _
                                    str(tr.CoordYValue * 1000#) + "   " + _
                                    str(tr.CoordZValue * 1000#) + "   "

                    ListBox2.AddItem str(Round(180 * rotZ.AngleValue / PI, 7)) + "   " + _
                                    str(Round(180 * rotY.AngleValue / PI, 7)) + "   " + _
                                    str(Round(180 * rotX.AngleValue / PI, 7))

                    Inserter_sub_module.Insert oldPartNum, motherProd.PartNumber, _
                                str(-tr.CoordXValue * 1000#), str(tr.CoordYValue * 1000#), str(tr.CoordZValue * 1000#), _
                                str(Round(180 * rotX.AngleValue / PI, 7)), str(Round(180 * rotY.AngleValue / PI, 7)), _
                                str(Round(180 * rotZ.AngleValue / PI, 7)), "mm", "deg"

                End If
            Next j

        End If
    Next i

End Sub

Private Sub cmbExit_Click()

    End

End Sub
