Attribute VB_Name = "MultiViewer"
Sub CATMain()

    frmViewer.Show vbModeless

End Sub

Attribute VB_Name = "frmViewer"
Attribute VB_Base = "0{57718705-B989-4E9F-A508-1AF653FEF9D9}{4B3280F1-3D7C-4472-8AF1-5ED39AE0A223}"
Attribute VB_GlobalNameSpace = False
Attribute VB_Creatable = False
Attribute VB_PredeclaredId = True
Attribute VB_Exposed = False
Attribute VB_TemplateDerived = False
Attribute VB_Customizable = False
Option Explicit

Private Sub UserForm_Initialize()
    
On Error Resume Next
    
    ' Get the active product document
    Dim actDoc As Document
    Set actDoc = CATIA.ActiveDocument

    ' Exit if the open document is not a product document
    If (TypeName(actDoc) <> "ProductDocument") Then
        MsgBox "The active document must be product document!", vbCritical
        End
    End If

    Dim prodDoc As ProductDocument
    Set prodDoc = actDoc

    ' Show the open product path in GUI
    textLine.Text = prodDoc.Path

    ' ------------------------------------------------------------------------

    ' Prepare the temporary folder
    Dim theFileSystem ' As FileSystem
    Set theFileSystem = CATIA.FileSystem

    Dim tmpFolderPath As String
    tmpFolderPath = Environ("Temp") + "\BuilderViewer\"

    ' Delete the temporary folder if it already exists
    If (theFileSystem.FolderExists(tmpFolderPath)) Then
        theFileSystem.DeleteFolder tmpFolderPath
    End If

    ' Create the temporary folder
    'Dim Fold4Viewer As Folder
    'Set Fold4Viewer =
    theFileSystem.CreateFolder tmpFolderPath

    ' Show the temporary folder path in GUI
    frmViewer.txtTmpPath.Text = tmpFolderPath

'    ' ------------------------------------------------------------------------
'
'    ' Copy the open product from its current folder into the temporary folder
'    Dim cloneProdPath As String
'    cloneProdPath = tmpFolderPath + prodDoc.Name
'    Call CloneProduct(tmpFolderPath)
'
'    ' Close the current (original) product
'    prodDoc.Close
'
'    ' Open the clone product
'    CATIA.Documents.Open cloneProdPath

End Sub

Private Sub CommandButton1_Click()

    ' Get the active product document
    Dim actDoc As Document
    Set actDoc = CATIA.ActiveDocument
    
    ' Exit if the open document is not a product document
    If (TypeName(actDoc) <> "ProductDocument") Then
        MsgBox "The active document must be product document!", vbCritical
        End
    End If
    
    Dim prodDoc As ProductDocument
    Set prodDoc = actDoc

    Call Analyze(prodDoc.Product)

End Sub

Private Sub CommandButton2_Click()

    End
    
End Sub

Private Sub CloneProduct(destPath As String)

    Dim docs As Documents
    Set docs = CATIA.Documents
    
    Dim i As Integer
    For i = 1 To docs.Count
        Dim doc As Document
        Set doc = docs.Item(i)
        doc.SaveAs destPath + doc.Name
    Next i

End Sub

Private Sub Analyze(prod As Product)

    ' Loop over the components of the top product and call the RemoveBody() method for each corresponding part
    Dim prods As Products
    Set prods = prod.Products

    Dim iProd As Integer
    For iProd = 1 To prods.Count
    
        Dim childProd As Product
        Set childProd = prods.Item(iProd)
        
        Call RemoveBody(childProd.ReferenceProduct.Parent.Part)
    
    Next iProd

End Sub

Private Sub RemoveBody(workPart As Part)

    ' Loop over all 'child' bodies and remove them from the PartBody
    Dim Wzk3D As ShapeFactory
    Set Wzk3D = workPart.ShapeFactory

    Dim bds As Bodies
    Set bds = workPart.Bodies

    Dim nBodies As Integer
    nBodies = bds.Count
    
    Dim i As Integer
    For i = 2 To nBodies
        workPart.InWorkObject = workPart.MainBody
        Wzk3D.AddNewRemove bds.Item(2) ' Yes, 2!
        workPart.Update
    Next i

End Sub
