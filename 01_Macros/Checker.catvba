Attribute VB_Name = "Checker"
Sub CATMain()

    MsgBox "Please, save all open documents before running the Checker!", vbInformation

    formChecker.Show vbModeless

End Sub

Attribute VB_Name = "formChecker"
Attribute VB_Base = "0{AF370D26-C398-4F42-B02E-98566EEC9942}{99D0FC25-6B17-4A1B-95A7-62CC46BD299A}"
Attribute VB_GlobalNameSpace = False
Attribute VB_Creatable = False
Attribute VB_PredeclaredId = True
Attribute VB_Exposed = False
Attribute VB_TemplateDerived = False
Attribute VB_Customizable = False
Option Explicit

Const STEPADD = 0.002
Const CIRCSHIFT = 0.02

Enum addendsChange
    deleteAddends
    restoreAddends
End Enum

Dim errorFound As Boolean

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument
    
    ' Translate to design mode
'    MsgBox "Parts in this product are to be translated into 'Design Mode'" + vbNewLine + "This may take a few minutes, please wait.", vbExclamation, "Translate to Design mode"
'    prodDoc.Product.ApplyWorkMode DESIGN_MODE

End Sub

Private Sub cmbStart_Click()

    ' GUI
    chkLinks.Enabled = False
    chkMothDaught.Enabled = False
    chkNeighbours.Enabled = False
    cmbStart.Enabled = False

    errorFound = False
    
    Dim docs As Documents
    Dim prtDoc As PartDocument
    Dim prt As Part
    Dim bds As Bodies
    
    Set docs = CATIA.Documents

    Dim i As Integer
    Dim j As Integer

    For i = 1 To docs.Count

'        If (docs.Item(i).Name <> "RICH_small_frame_container.CATPart") And _
'            (docs.Item(i).Name <> "RICH_mainframe_1.CATPart") And _
'            (docs.Item(i).Name <> "RICH_mainframe_2.CATPart") Then
        

        lblStatus.Caption = "Checking document " + Str(i) + " of " + Str(docs.Count)

        If Right(docs.Item(i).Name, 8) = ".CATPart" Then
            Set prtDoc = docs.Item(i)
            Set prt = prtDoc.Part
            Set bds = prt.Bodies

            ' Temporary delete STEPADD and CIRCSHIFT
            deleteOrRestoreAddends prtDoc, addendsChange.deleteAddends

' Not yet implemented
'            BooleanCheck bds.Item(1)

            ' Check whether this volume is an assembly-volume by material
            Dim params As Parameters
            Dim matParam As Parameter
            Set params = prt.Parameters
            Set matParam = params.GetItem("Material")
            Dim isVAss As Boolean
            isVAss = False
            If matParam.ValueAsString = "Assembly" Then isVAss = True

            ' Check rotation names
            If CheckRotates(params) = False Then
                errorFound = True
            End If

            ' Mother-daughter check
            ' If this is an assembly-volume then skip mother-daughter check
            If isVAss = False And chkMothDaught.Value = True Then
                For j = 2 To bds.Count
                    lblStatus2.Caption = "Checking mother-daughter " + Str(j - 1) + " of " + Str(bds.Count - 1)
                    If InnerCheck(prtDoc, bds.Item(j)) = False Then
                        formErrorList.lstErrors.AddItem (docs.Item(i).Name + ": '" + bds.Item(j).Name + "' intersects the bounds of its mother volume")
                        errorFound = True
                    End If
                Next j
                lblStatus2.Caption = ""
            End If

            ' Links check
            If chkLinks.Value = True Then
                For j = 2 To bds.Count
                    lblStatus2.Caption = "Checking links " + Str(j - 1) + " of " + Str(bds.Count - 1)
                    If LinkCheck(bds.Item(j), docs.Item(i).Name) = False Then
                        errorFound = True
                    End If
                Next j
                lblStatus2.Caption = ""
            End If

            ' Neighbours check
            If chkNeighbours.Value = True Then
                If NeighbourCheck(prtDoc) = False Then
                    errorFound = True
                End If
            End If

            ' Restore STEPADD and CIRCSHIFT
            deleteOrRestoreAddends prtDoc, addendsChange.restoreAddends
        End If


'        Else
'            MsgBox docs.Item(i).Name
'        End If

    Next i

    If errorFound = True Then
        formErrorList.Show False
        Unload Me
    Else
        lblStatus.Caption = "Done! No errors found."
    End If

End Sub

' Check naming of translations and rotations for boolean operands
' Returns 1 if OK
' Returns 0 if Error
Function BooleanCheck(db As Body)

End Function

Function CheckRotates(params As Parameters)

    Dim i As Integer
    Dim param As Parameter
    Dim inStrPos As Integer
    Dim chkStr As String

    CheckRotates = True

    For i = 1 To params.Count
        Set param = params.Item(i)
        inStrPos = InStr(param.Name, "Rotate.")
        If inStrPos <> 0 Then
            chkStr = Mid(param.Name, inStrPos + 7, 1)
            If chkStr <> "X" And chkStr <> "Y" And chkStr <> "Z" And _
                chkStr <> "x" And chkStr <> "y" And chkStr <> "z" Then

                formErrorList.lstErrors.AddItem "Parameter '" + param.Name + "' has incorrect name"
                CheckRotates = False

            End If
        End If
    Next i

End Function


' Check that the name of the body corresponds to the linked volume
' Returns true if OK
' Returns false if Error
Function LinkCheck(bd As Body, motherName As String) As Boolean

    Dim sol As Solid
    Dim srcProd As Product
    Set sol = bd.Shapes.Item(1)
    Set srcProd = sol.SourceProduct

    Dim correctPrefix As String
    correctPrefix = "Body." + srcProd.PartNumber + "."

    If Left(bd.Name, Len(correctPrefix)) <> correctPrefix Then
        formErrorList.lstErrors.AddItem (motherName + ": '" + bd.Name + "' has incorrect name. " + _
            "It refers to '" + srcProd.PartNumber + "' so it must begin with '" + correctPrefix + "'")
        LinkCheck = False
    Else
        LinkCheck = True
    End If

End Function

' Удаление STEPADD and CIRCSHIFT, служащих для красивой визуализации, но мешающих чекеру
Sub deleteOrRestoreAddends(prtDoc As PartDocument, changeType As addendsChange)

    Dim bds As Bodies
    Set bds = prtDoc.Part.Bodies

    Dim bd As Body
    Dim shps As Shapes
    Dim shp As Shape

    Dim i As Integer
    Dim j As Integer

    For i = 1 To bds.Count
        Set bd = bds.Item(i)
        Set shps = bd.Shapes
        For j = 1 To shps.Count
            Set shp = shps.Item(j)
            If Left(shp.Name, Len("Replica.X")) = "Replica.X" Or _
                Left(shp.Name, Len("Replica.Y")) = "Replica.Y" Or _
                Left(shp.Name, Len("Replica.Z")) = "Replica.Z" Then
                    If (changeType = deleteAddends) Then
                        shp.FirstDirectionRepartition.Spacing.Value = shp.FirstDirectionRepartition.Spacing.Value - STEPADD
                    ElseIf (changeType = restoreAddends) Then
                        shp.FirstDirectionRepartition.Spacing.Value = shp.FirstDirectionRepartition.Spacing.Value + STEPADD
                    End If
            ElseIf Left(shp.Name, Len("Replica.P")) = "Replica.P" Then
                    If (changeType = deleteAddends) Then
                        shp.AngularRepartition.AngularSpacing.Value = shp.AngularRepartition.AngularSpacing.Value - CIRCSHIFT
                    ElseIf (changeType = restoreAddends) Then
                        shp.AngularRepartition.AngularSpacing.Value = shp.AngularRepartition.AngularSpacing.Value + CIRCSHIFT
                    End If
            End If
        Next j
    Next i

    ' Update
    prtDoc.Part.Update

End Sub

' Проверка, не пересекаются ли объёмы на одном уровне вложенности
' Returns true if OK
' Returns false if Error
Function NeighbourCheck(prtDoc As PartDocument) As Boolean

    Dim prt As Part
    Dim bds As Bodies
    Dim sel As Selection
    Set prt = prtDoc.Part
    Set bds = prt.Bodies
    Set sel = CATIA.ActiveDocument.Selection
    
    Dim i As Integer
    Dim j As Integer
    Dim op1 As Body
    Dim op2 As Body
    Dim rez As Body
    Dim shpF As ShapeFactory
    Set shpF = prt.ShapeFactory
    
    Dim isOK As Boolean
    isOK = True
    For i = 2 To bds.Count - 1
        For j = i + 1 To bds.Count

            lblStatus2.Caption = "Checking neighbours " + Str(i - 1) + " of " + Str(bds.Count - 2)
            sel.Clear
            sel.Add bds.Item(i)
            sel.Copy
            sel.PasteSpecial "CATPrtResultWithOutLink"
            Set op1 = bds.Item(bds.Count)
    
            sel.Clear
            sel.Add bds.Item(j)
            sel.Copy
            sel.PasteSpecial "CATPrtResultWithOutLink"
            Set op2 = bds.Item(bds.Count)
    
            sel.Clear
            prt.InWorkObject = op1
            shpF.AddNewIntersect op2
            Set rez = bds.Item(bds.Count)
    
            ' Здесь надо отловить сообщение об ошибке, типа 'No resulting element'
            ' Если оно есть, то хорошо, а если нет, то надо бы прервать цикл и выдать сообщение
            ' о наличии пересекающихся объёмов на одном уровне вложенности
    
    On Error GoTo ErrHandler
            prt.UpdateObject rez
            'MsgBox "Error"
            isOK = False

            formErrorList.lstErrors.AddItem (prtDoc.Name + ": '" + op1.Name + "'  intersects  '" + op2.Name + "'")

AfterError:
            sel.Add rez
            sel.Delete
            If isOK = False Then
                lblStatus2.Caption = ""
                NeighbourCheck = False
                Exit Function
            End If
        Next
    Next
    
    lblStatus2.Caption = ""
    NeighbourCheck = True
    Exit Function
    
ErrHandler:
        'MsgBox Err.Number
        If (Err.Number = -2147467259 Or Err.Number = 0) Then
            'MsgBox "OK"
        End If
        Resume AfterError
        
End Function

' Проверка, не выходят ли внутренние объёмы за пределы внешнего
' Returns true if OK
' Returns false if Error
Function InnerCheck(prtDoc As PartDocument, bd As Body) As Boolean

    Dim prt As Part
    Dim bds As Bodies
    Dim sel As Selection
    Set prt = prtDoc.Part
    Set bds = prt.Bodies
    Set sel = CATIA.ActiveDocument.Selection
    
    Dim worldToAdd As Body
    Dim worldToRemove As Body
    Dim bodyToAdd As Body
    Dim shpF As ShapeFactory
    
    sel.Clear
    
    sel.Add bds.Item("PartBody")
    sel.Copy
    sel.PasteSpecial "CATPrtResultWithOutLink"
    sel.Clear
    Set worldToRemove = bds.Item(bds.Count)
    
    sel.Add bd
    sel.Copy
    sel.PasteSpecial "CATPrtResultWithOutLink"
    sel.Clear
    Set bodyToAdd = bds.Item(bds.Count)
    
    prt.InWorkObject = bodyToAdd
    Set shpF = prt.ShapeFactory
    shpF.AddNewRemove worldToRemove
    
    Dim rez As Body
    Set rez = bds.Item(bds.Count)
    
    ' Здесь надо отловить сообщение об ошибке, типа 'No resulting element'
    ' Если оно есть, то хорошо, а если нет, то ... как обычно
    
    On Error GoTo ErrHandler
            prt.UpdateObject rez
    '        MsgBox "Error"
            InnerCheck = False
    
AfterError:
        sel.Add rez
        sel.Delete
    Exit Function
    
ErrHandler:
        'MsgBox Err.Number
        If (Err.Number = -2147467259 Or Err.Number = 0) Then
            'MsgBox "OK"
            InnerCheck = True
        End If
        Resume AfterError
        
End Function

Private Sub cmbExit_Click()

    End

End Sub

Attribute VB_Name = "formErrorList"
Attribute VB_Base = "0{19777807-A59C-4FD8-9F98-C518FEF54923}{2C07B994-7AA9-49FF-A972-6197ADDD2175}"
Attribute VB_GlobalNameSpace = False
Attribute VB_Creatable = False
Attribute VB_PredeclaredId = True
Attribute VB_Exposed = False
Attribute VB_TemplateDerived = False
Attribute VB_Customizable = False
Private Sub cmbClose_Click()

    End

End Sub
