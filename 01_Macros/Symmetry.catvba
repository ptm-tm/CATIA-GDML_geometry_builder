Attribute VB_Name = "CommonDigitalString"
Option Explicit

Public Function unitConvert(unit As String) As Double

    Dim PI As Double
    PI = 3.14159265358979
    Select Case unit
        Case "mm"
            unitConvert = 1#
        Case "cm"
            unitConvert = 10#
        Case "m"
            unitConvert = 1000#
        Case "deg"
            unitConvert = 1#
        Case "degree"
            unitConvert = 1#
        Case "radian"
            unitConvert = 180# / PI
    End Select

End Function

Public Function isNum(str As String) As Boolean

    Dim i As Integer
    Dim flag As Boolean
    flag = False
    isNum = True
    For i = 1 To Len(str)
        If isDigit(Mid(str, i, 1)) = False Then
            isNum = False
        End If
    Next

End Function

Public Function isDigit(str As String) As Boolean

    Dim arr(0 To 9) As String
    Dim i As Integer
    arr(0) = "0"
    arr(1) = "1"
    arr(2) = "2"
    arr(3) = "3"
    arr(4) = "4"
    arr(5) = "5"
    arr(6) = "6"
    arr(7) = "7"
    arr(8) = "8"
    arr(9) = "9"
    isDigit = False
    For i = 0 To 9
        If str = arr(i) Then
            isDigit = True
        End If
    Next

End Function

Attribute VB_Name = "Inserter_sub_module"
Option Explicit

Function Insert(childVolumeName As String, _
            motherVolumeName As String, _
            x As String, y As String, z As String, _
            xr As String, yr As String, zr As String, _
            lunit As String, aunit As String) As Part

    Dim i As Integer
    Dim ProductDoc As ProductDocument
    Dim partDoc As PartDocument
    Dim docs As Documents
    Dim pub As Publication
    Dim sel As Selection
    
    Set sel = CATIA.ActiveDocument.Selection
    Set ProductDoc = CATIA.ActiveDocument
    Set docs = CATIA.Documents
    
    'coincidence_std_planes         ' is it needed here?
    
    For i = 1 To ProductDoc.Product.Products.Count
        If (ProductDoc.Product.Products.Item(i).PartNumber = childVolumeName) Then
            Set pub = ProductDoc.Product.Products.Item(i).Publications.Item("PartBody")
            Exit For
        End If
    Next
    
    For i = 1 To docs.Count
        If (Right(docs.Item(i).Name, 8) = ".CATPart") Then
            If (docs.Item(i).Product.PartNumber = motherVolumeName) Then
                Set partDoc = docs.Item(i)
                Exit For
            End If
        End If
    Next
    
    'copy - paste - as result with link
    sel.Clear
    sel.Add pub
    sel.Copy
    sel.Clear
    sel.Add partDoc.Part
    sel.PasteSpecial "CATPrtResult"
    sel.Clear
    
    'rename recent copied body
    partDoc.Part.Bodies.Item(partDoc.Part.Bodies.Count).Name = nameGenerate(partDoc, childVolumeName)
    
    'position
    ProcessBodyPosition partDoc.Part, partDoc.Part.Bodies.Item(partDoc.Part.Bodies.Count), x, y, z, xr, yr, zr, lunit, aunit
    
    Set Insert = partDoc.Part

End Function

Sub ProcessBodyPosition(prt As Part, bd As Body, _
                        x As String, y As String, z As String, _
                        xr As String, yr As String, zr As String, _
                        lunit As String, aunit As String)

    Dim hybShpFactory As HybridShapeFactory
    Dim shpFactory As ShapeFactory
    Dim origin As OriginElements
    Dim hybShpRotX As HybridShapeRotate
    Dim hybShpRotY As HybridShapeRotate
    Dim hybShpRotZ As HybridShapeRotate
    Dim hybShpTrans As HybridShapeTranslate
    Dim rotX As Rotate
    Dim rotY As Rotate
    Dim rotZ As Rotate
    Dim trans As Translate
    Dim sel As Selection
    Dim visPropSet As VisPropertySet
    Dim refAxisX As Reference
    Dim refAxisY As Reference
    Dim refAxisZ As Reference
    Dim refPlaneXY As Reference
    Dim refPlaneYZ As Reference
    Dim refPlaneZX As Reference
    Dim Intersection_XY_ZX As HybridShapeIntersection
    Dim Intersection_YZ_XY As HybridShapeIntersection
    Dim Intersection_ZX_YZ As HybridShapeIntersection
    
    Set hybShpFactory = prt.HybridShapeFactory
    Set shpFactory = prt.ShapeFactory
    Set origin = prt.OriginElements
    Set refPlaneXY = prt.CreateReferenceFromObject(origin.PlaneXY)
    Set refPlaneYZ = prt.CreateReferenceFromObject(origin.PlaneYZ)
    Set refPlaneZX = prt.CreateReferenceFromObject(origin.PlaneZX)
    Set sel = CATIA.ActiveDocument.Selection
    Set visPropSet = sel.VisProperties
    
    'Z axis preparation
    Set Intersection_ZX_YZ = hybShpFactory.AddNewIntersection(refPlaneZX, refPlaneYZ)
    Intersection_ZX_YZ.PointType = 0
    bd.InsertHybridShape Intersection_ZX_YZ
    prt.InWorkObject = Intersection_ZX_YZ
    Intersection_ZX_YZ.Name = "Z axis"
    sel.Clear
    sel.Add Intersection_ZX_YZ
    visPropSet.SetShow catVisPropertyNoShowAttr
    sel.Clear
    prt.Update
    'Y axis preparation
    Set Intersection_YZ_XY = hybShpFactory.AddNewIntersection(refPlaneYZ, refPlaneXY)
    Intersection_YZ_XY.PointType = 0
    bd.InsertHybridShape Intersection_YZ_XY
    prt.InWorkObject = Intersection_YZ_XY
    Intersection_YZ_XY.Name = "Y axis"
    sel.Clear
    sel.Add Intersection_YZ_XY
    visPropSet.SetShow catVisPropertyNoShowAttr
    sel.Clear
    prt.Update
    'X axis preparation
    Set Intersection_XY_ZX = hybShpFactory.AddNewIntersection(refPlaneXY, refPlaneZX)
    Intersection_XY_ZX.PointType = 0
    bd.InsertHybridShape Intersection_XY_ZX
    prt.InWorkObject = Intersection_XY_ZX
    Intersection_XY_ZX.Name = "X axis"
    sel.Clear
    sel.Add Intersection_XY_ZX
    visPropSet.SetShow catVisPropertyNoShowAttr
    sel.Clear
    prt.Update
    
    'Rotate by Z axis creation
    Set refAxisZ = prt.CreateReferenceFromObject(Intersection_ZX_YZ)
    Set rotZ = shpFactory.AddNewRotate2(refAxisZ, Val(zr) * unitConvert(aunit))
    Set hybShpRotZ = rotZ.HybridShape
    hybShpRotZ.RotationType = 0
    hybShpRotZ.Axis = refAxisZ
    hybShpRotZ.Name = "Rotate.Z"
    prt.InWorkObject = hybShpRotZ
    prt.Update
    'Rotate by Y axis creation
    Set refAxisY = prt.CreateReferenceFromObject(Intersection_YZ_XY)
    Set rotY = shpFactory.AddNewRotate2(refAxisY, Val(yr) * unitConvert(aunit))
    Set hybShpRotY = rotY.HybridShape
    hybShpRotY.RotationType = 0
    hybShpRotY.Axis = refAxisY
    hybShpRotY.Name = "Rotate.Y"
    prt.InWorkObject = hybShpRotY
    prt.Update
    'Rotate by X axis creation
    Set refAxisX = prt.CreateReferenceFromObject(Intersection_XY_ZX)
    Set rotX = shpFactory.AddNewRotate2(refAxisX, Val(xr) * unitConvert(aunit))
    Set hybShpRotX = rotX.HybridShape
    hybShpRotX.RotationType = 0
    hybShpRotX.Axis = refAxisX
    hybShpRotX.Name = "Rotate.X"
    prt.InWorkObject = hybShpRotX
    prt.Update
    
    'Translation
    Set trans = shpFactory.AddNewTranslate2(0)
    Set hybShpTrans = trans.HybridShape
    hybShpTrans.VectorType = 2
    hybShpTrans.CoordXValue = Val(x) * unitConvert(lunit) / 1000#
    hybShpTrans.CoordYValue = Val(y) * unitConvert(lunit) / 1000#
    hybShpTrans.CoordZValue = Val(z) * unitConvert(lunit) / 1000#
    prt.InWorkObject = hybShpTrans
    prt.Update

End Sub

Function nameGenerate(partDoc As PartDocument, base As String) As String

    Dim prefixLine As String
    Dim indexLine As String
    Dim i As Integer
    Dim maxIndex As Integer
    prefixLine = "Body." & base & "."
    maxIndex = 0
    For i = 1 To partDoc.Part.Bodies.Count
        If (StrComp(Mid(partDoc.Part.Bodies.Item(i).Name, 1, Len(prefixLine)), prefixLine, vbTextCompare) = 0) Then
            indexLine = Mid(partDoc.Part.Bodies.Item(i).Name, Len(prefixLine) + 1)
            If ((isNum(indexLine) = True) And (Val(indexLine) > maxIndex)) Then
                maxIndex = Val(indexLine)
            End If
        End If
    Next
    nameGenerate = prefixLine & (maxIndex + 1)

End Function

Attribute VB_Name = "Support"
Option Explicit

Function PrimitiveType(prt As Part) As String

    Dim pType As String
    pType = prt.Bodies.Item("PartBody").Shapes.Item(1).Name
                
    If (InStr(pType, "G4Trap")) Then
        pType = "G4Trap"
    ElseIf (InStr(pType, "G4Box")) Then
        pType = "G4Box"
    ElseIf (InStr(pType, "G4Sphere")) Then
        pType = "G4Sphere"
    Else
        pType = ""
    End If
    PrimitiveType = pType

End Function

' Проверка на симметричность
Function SymCheck(prt As Part, plane As String, ByRef parVals As Collection, ByVal pType As String) As Boolean

    SymCheck = False
    Dim params As Parameters
    Set params = prt.Parameters
    
    'Считываем параметры в коллекцию
    Set parVals = ParamToCollection(params, pType)
    'Проверяем на симметричность в зависимости от плоскости и типа примитива
    Select Case pType
        Case "G4Trap":
            Select Case plane
                Case "XY":
                    If (parVals.Item("pTheta") = "0deg" And parVals.Item("pDx1") = parVals.Item("pDx3") And _
                        parVals.Item("pDx2") = parVals.Item("pDx4") And parVals.Item("pDy1") = parVals.Item("pDy2")) Then
                            SymCheck = True
                    End If
                Case "ZX":
                     If (parVals.Item("pPhi") = "0deg" And parVals.Item("pDx1") = parVals.Item("pDx2") And _
                        parVals.Item("pDx3") = parVals.Item("pDx4") And parVals.Item("pAlp1") = "0deg") Then
                            SymCheck = True
                    End If
                Case "YZ":
                    If (parVals.Item("pAlp1") = "0deg" And (parVals.Item("pTheta") = "180deg" Or parVals.Item("pTheta") = "0deg")) Then
                            SymCheck = True
                    End If
            End Select
    End Select

End Function

' Считывание параметров примитива в коллекцию
Function ParamToCollection(params As Parameters, pType As String) As Collection

    Dim param As Parameter
    Dim parVals As New Collection
    
    Dim j As Integer

    Select Case pType
        Case "G4Box":
            For j = 1 To params.Count
                Set param = params.Item(j)

                If (InStr(param.Name, "pX")) Then
                    parVals.Add param.ValueAsString, "pX"
                ElseIf (InStr(param.Name, "pY")) Then
                    parVals.Add param.ValueAsString, "pY"
                ElseIf (InStr(param.Name, "pZ")) Then
                    parVals.Add param.ValueAsString, "pZ"
                End If
            Next j

        Case "G4Trap":
            For j = 1 To params.Count
                Set param = params.Item(j)
        
                If (InStr(param.Name, "pDz")) Then
                    parVals.Add param.ValueAsString, "pDz"
                ElseIf (InStr(param.Name, "pTheta")) Then
                    parVals.Add param.ValueAsString, "pTheta"
                ElseIf (InStr(param.Name, "pPhi")) Then
                    parVals.Add param.ValueAsString, "pPhi"
                ElseIf (InStr(param.Name, "pDy1")) Then
                    parVals.Add param.ValueAsString, "pDy1"
                ElseIf (InStr(param.Name, "pDx1")) Then
                    parVals.Add param.ValueAsString, "pDx1"
                ElseIf (InStr(param.Name, "pDx2")) Then
                    parVals.Add param.ValueAsString, "pDx2"
                ElseIf (InStr(param.Name, "pAlp1")) Then
                    parVals.Add param.ValueAsString, "pAlp1"
                ElseIf (InStr(param.Name, "pDy2")) Then
                    parVals.Add param.ValueAsString, "pDy2"
                ElseIf (InStr(param.Name, "pDx3")) Then
                    parVals.Add param.ValueAsString, "pDx3"
                ElseIf (InStr(param.Name, "pDx4")) Then
                    parVals.Add param.ValueAsString, "pDx4"
                End If
            Next j

    End Select

    Set ParamToCollection = parVals

End Function

Attribute VB_Name = "Symmetry"
Sub CATMain()

    formSymmetry.Show

End Sub

Attribute VB_Name = "formSymmetry"
Attribute VB_Base = "0{EB68C632-2B9F-476E-A941-24DC4A99C249}{733B2372-E453-460A-B84D-E8EED625299B}"
Attribute VB_GlobalNameSpace = False
Attribute VB_Creatable = False
Attribute VB_PredeclaredId = True
Attribute VB_Exposed = False
Attribute VB_TemplateDerived = False
Attribute VB_Customizable = False
Option Explicit

Const PI = 3.14159265358979

Private Sub UserForm_Initialize()

    Dim activeDoc As Document
    Set activeDoc = CATIA.ActiveDocument

    'Is active document a product?
    If Right(activeDoc.Name, 11) <> ".CATProduct" Then
        MsgBox "The type of the active document must be a product", vbCritical, "Incorrect active document type"
        End
    End If

    Dim prodDoc As ProductDocument
    Set prodDoc = activeDoc
    Dim prod As Product
    Set prod = prodDoc.Product
    Dim subprods As Products
    Set subprods = prod.Products
    
    Dim i As Integer
    
    For i = 1 To subprods.Count
        ComboBox1.AddItem subprods.Item(i).PartNumber
    Next i

    ComboBox1.Text = ComboBox1.List(ComboBox1.ListCount - 1)

End Sub

Private Sub cmbList_Click()

    Dim docs As Documents
    Set docs = CATIA.Documents
    Dim mPrtDoc As PartDocument
    Set mPrtDoc = docs.Item(ComboBox1.Text & ".CATPart")
    Dim mPrt As Part
    Set mPrt = mPrtDoc.Part
    Dim i As Integer
    
    For i = 1 To mPrt.Bodies.Count
        ListBox1.AddItem mPrt.Bodies.Item(i).Name
    Next i

End Sub

Private Sub cmbStart_Click()

    Dim i As Integer
    Dim prodDoc As ProductDocument
    Dim sel As Selection
    Dim prod As Product
    Dim subprods As Products
    
    Dim oldProd As Product
    Dim newProd As Product
    
    Dim oldName As String
    Dim newName As String
    
    Dim oldPrtNum As String
    Dim newPrtNum As String
    
    Dim newDoc As Document
    Dim newPartDoc As PartDocument
    Dim oldPrtDoc As PartDocument
    
    Dim oldPrt As Part
    Dim newPrt As Part
    
    Dim params As Parameters
    Dim param As Parameter
    Dim j As Integer
    Dim k As Integer
    
    Dim motherProd As Product
    Dim motherPartDoc As PartDocument
    Dim motherPart As Part
    Dim motherBodies As Bodies
    Dim bd As Body
    Dim shps As Shapes
    
    Dim rotZ As HybridShapeRotate
    Dim rotY As HybridShapeRotate
    Dim rotX As HybridShapeRotate
    Dim tr As HybridShapeTranslate
    
    Set prodDoc = CATIA.ActiveDocument
    Set sel = prodDoc.Selection
    Set prod = prodDoc.Product
    Set subprods = prod.Products
    
    Dim plane As String
    'Получение плоскости симметрирования
    If (formPlaneXY.Value) Then
        plane = "XY"
    ElseIf (formPlaneZX.Value) Then
        plane = "ZX"
    ElseIf (formPlaneYZ.Value) Then
        plane = "YZ"
    End If
    
    'Получение материского объема
    Dim docs As Documents
    Set docs = CATIA.Documents
    Set motherPartDoc = docs.Item(ComboBox1.Text & ".CATPart")
    
    Set motherPart = motherPartDoc.Part
    Set motherBodies = motherPart.Bodies
    
    Dim oldBody As Body
    Dim parVals As New Collection
    
    For i = 0 To ListBox1.ListCount - 1
        If ListBox1.Selected(i) = True Then
        
            'Получение объема для создания симметричного ему
            Set oldBody = motherBodies.Item(ListBox1.List(i))
            Set oldPrtDoc = docs.Item(oldBody.Shapes.Item(1).SourceProduct.PartNumber & ".CATPart")
            Set oldPrt = oldPrtDoc.Part
            oldName = oldPrt.Name
            Set oldProd = subprods.GetItem(oldName & ".1")
            oldPrtNum = oldProd.PartNumber
            
            'Определяем тип примитива
            Dim pType As String
            pType = PrimitiveType(oldPrt)
            If (pType = "") Then
                MsgBox "Primitive type error!"
                Exit Sub
            End If
            
            'Провека симметричности примитива
            Dim isSym As Boolean
            Select Case pType
                Case "G4Trap":
                    isSym = SymCheck(oldPrt, plane, parVals, pType)
                Case Else
                    isSym = True
            End Select

            'Получение поворотов и траслейтов
            Set shps = oldBody.HybridShapes
            Set rotZ = shps.GetItem("Rotate.Z")
            Set rotY = shps.GetItem("Rotate.Y")
            Set rotX = shps.GetItem("Rotate.X")

            For k = 1 To shps.Count
                If InStr(shps.Item(k).Name, "Translate.") > 0 Then
                    Set tr = shps.Item(k)
                    Exit For
                End If
            Next k
            
            'если примитив симметричен, то вствляем уже существующий с новыми поворотами  смещениями
            If (isSym) Then
               Select Case plane
                    Case "ZX":
                       Inserter_sub_module.Insert oldName, motherPart.Name, _
                                    str(tr.CoordXValue * 1000#), str(-tr.CoordYValue * 1000#), str(tr.CoordZValue * 1000#), _
                                    str(Round(360 - 180 * rotX.AngleValue / PI, 7)), str(Round(180 * rotY.AngleValue / PI, 7)), _
                                    str(Round(360 - 180 * rotZ.AngleValue / PI, 7)), "mm", "deg"
                    Case "XY":
                       Inserter_sub_module.Insert oldName, motherPart.Name, _
                                    str(tr.CoordXValue * 1000#), str(tr.CoordYValue * 1000#), str(-tr.CoordZValue * 1000#), _
                                    str(Round(360 - 180 * rotX.AngleValue / PI, 7)), str(Round(360 - 180 * rotY.AngleValue / PI, 7)), _
                                    str(Round(180 * rotZ.AngleValue / PI, 7)), "mm", "deg"
                    Case "YZ":
                       Inserter_sub_module.Insert oldName, motherPart.Name, _
                                    str(-tr.CoordXValue * 1000#), str(tr.CoordYValue * 1000#), str(tr.CoordZValue * 1000#), _
                                    str(Round(180 * rotX.AngleValue / PI, 7)), str(Round(360 - 180 * rotY.AngleValue / PI, 7)), _
                                    str(Round(360 - 180 * rotZ.AngleValue / PI, 7)), "mm", "deg"
               End Select
            'если примитив не симметричен, то создаем еще один Part с изменненными параметрами
            Else
                sel.Clear
                sel.Add oldProd
                sel.Copy
                
                sel.Clear
                sel.Add prod
                sel.PasteSpecial "CATSpecBreakLink"
                sel.Clear
                
                newPrtNum = oldPrtNum + ".sym"
                Dim symNr As Integer
                symNr = 1
                For k = 1 To subprods.Count
                    If InStr(subprods.Item(k).PartNumber, newPrtNum) Then
                        symNr = symNr + 1
                    End If
                Next k
                Set newProd = subprods.Item(subprods.Count)
                newPrtNum = oldPrtNum + ".sym" + Trim(str(symNr))
                newName = newPrtNum + ".1"
                
                newProd.PartNumber = newPrtNum
                newProd.Name = newName
            
                Set newDoc = CATIA.Documents.Item(CATIA.Documents.Count)
                If (CATIA.FileSystem.FileExists(oldPrtDoc.Path + "\" + newPrtNum + ".CATPart")) Then
                    CATIA.FileSystem.DeleteFile (oldPrtDoc.Path + "\" + newPrtNum + ".CATPart")
                End If
                newDoc.SaveAs oldPrtDoc.Path + "\" + newPrtNum + ".CATPart"
                Set newPartDoc = newDoc
                Set newPrt = newPartDoc.Part
                Set params = newPrt.Parameters
                Select Case plane
                    Case "XY":
                        For j = 1 To params.Count
                            Set param = params.Item(j)
            
                            If (InStr(param.Name, "pDx1")) Then
                                        param.ValuateFromString parVals.Item("pDx4")
                            ElseIf (InStr(param.Name, "pDx2")) Then
                                        param.ValuateFromString parVals.Item("pDx3")
                            ElseIf (InStr(param.Name, "pDx3")) Then
                                        param.ValuateFromString parVals.Item("pDx2")
                            ElseIf (InStr(param.Name, "pDx4")) Then
                                        param.ValuateFromString parVals.Item("pDx1")
                            ElseIf (InStr(param.Name, "pDy1")) Then
                                        param.ValuateFromString parVals.Item("pDy2")
                            ElseIf (InStr(param.Name, "pDy2")) Then
                                        param.ValuateFromString parVals.Item("pDy1")
                            End If
            
                        Next j
                        
                        Inserter_sub_module.Insert newPrt.Name, motherPart.Name, _
                                            str(tr.CoordXValue * 1000#), str(tr.CoordYValue * 1000#), str(-tr.CoordZValue * 1000#), _
                                            str(Round(180 * rotX.AngleValue / PI, 7)), str(Round(180 * rotY.AngleValue / PI, 7)), _
                                            str(Round(180 + 180 * rotZ.AngleValue / PI, 7)), "mm", "deg"
                    Case "ZX":
                        For j = 1 To params.Count
                            Set param = params.Item(j)
            
                            If (InStr(param.Name, "pDx1")) Then
                                        param.ValuateFromString parVals.Item("pDx2")
                            ElseIf (InStr(param.Name, "pDx2")) Then
                                        param.ValuateFromString parVals.Item("pDx1")
                            ElseIf (InStr(param.Name, "pDx3")) Then
                                        param.ValuateFromString parVals.Item("pDx4")
                            ElseIf (InStr(param.Name, "pDx4")) Then
                                        param.ValuateFromString parVals.Item("pDx3")
                            End If
            
                        Next j
                        
                        Inserter_sub_module.Insert newPrt.Name, motherPart.Name, _
                                            str(tr.CoordXValue * 1000#), str(-tr.CoordYValue * 1000#), str(tr.CoordZValue * 1000#), _
                                            str(Round(180 * rotX.AngleValue / PI, 7)), str(Round(180 * rotY.AngleValue / PI, 7)), _
                                            str(Round(180 * rotZ.AngleValue / PI, 7)), "mm", "deg"
                    Case "YZ":
                         For j = 1 To params.Count
                            Set param = params.Item(j)
            
                            If (InStr(param.Name, "pPhi")) Then
                                        param.ValuateFromString str(Val(parVals.Item("pPhi")) + 180) & "deg"
                            End If
            
                        Next j
                        
                        Inserter_sub_module.Insert newPrt.Name, motherPart.Name, _
                                            str(-tr.CoordXValue * 1000#), str(tr.CoordYValue * 1000#), str(tr.CoordZValue * 1000#), _
                                            str(Round(180 * rotX.AngleValue / PI, 7)), str(Round(180 * rotY.AngleValue / PI, 7)), _
                                            str(Round(180 * rotZ.AngleValue / PI, 7)), "mm", "deg"
                End Select
                newPrt.Update
           End If
        End If
        Set parVals = Nothing
    Next i
    prod.Update
End Sub

Private Sub cmbExit_Click()

    End

End Sub
