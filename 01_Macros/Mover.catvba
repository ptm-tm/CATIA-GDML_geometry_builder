Attribute VB_Name = "Mover"
Sub CATMain()

    formMover.Show vbModeless

End Sub

Attribute VB_Name = "formMover"
Attribute VB_Base = "0{6DA324E5-1714-4E24-ACDC-583ABCBB4812}{19AD1C90-6462-44BB-B1E7-93587D66BABC}"
Attribute VB_GlobalNameSpace = False
Attribute VB_Creatable = False
Attribute VB_PredeclaredId = True
Attribute VB_Exposed = False
Attribute VB_TemplateDerived = False
Attribute VB_Customizable = False
Option Explicit

Private Sub ComboBox1_Change()
    
    Dim filter As String

    If (OptionButton1.Value = True) Then
        filter = textToFilter(ComboBox1.text)
        txtFilter.text = filter
    End If

End Sub

Private Sub CommandButton1_Click()

    formMoverHelp.Show vbModeless

End Sub

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument
    
    ' Translate to design mode
'    MsgBox "Parts in this product are to be translated into 'Design Mode'" + vbNewLine + "This may take a few minutes, please wait.", vbExclamation, "Translate to Design mode"
'    prodDoc.Product.ApplyWorkMode DESIGN_MODE

    'txtFilter.Text = "CoordX"

#If VBA7 Then

    ComboBox1.AddItem "Translation, X axis"
    ComboBox1.AddItem "Translation, Y axis"
    ComboBox1.AddItem "Translation, Z axis"
    
    ComboBox1.AddItem "Rotation, X axis"
    ComboBox1.AddItem "Rotation, Y axis"
    ComboBox1.AddItem "Rotation, Z axis"

#Else

    ComboBox1.AddItem "Translation, X axis"
    ComboBox1.AddItem "Translation, Y axis"
    ComboBox1.AddItem "Translation, Z axis"
    
    ComboBox1.AddItem "Rotation, X axis"
    ComboBox1.AddItem "Rotation, Y axis"
    ComboBox1.AddItem "Rotation, Z axis"

#End If

    lblStatus.Caption = "Specify the filter and press 'List' button."

End Sub

Private Sub cmbList_Click()

    Dim prodDoc As ProductDocument
    Dim prod As Product
    Dim params As Parameters
    Dim sel As Selection

    Set prodDoc = CATIA.ActiveDocument
    Set prod = prodDoc.Product
    Set params = prod.Parameters
    
    Set sel = prodDoc.Selection
    
    ' By now disable selection!
    ' todo - check and implement
    sel.Clear
    
    ' Beforehand clear the lists
    ListBox1.Clear
    ListBox2.Clear

    Dim i As Integer
    Dim k As Integer
    Dim selEl As SelectedElement
    Dim param As Parameter


    ' Select the filter
    Dim filter As String
    
    If (OptionButton1.Value = True) Then
        filter = textToFilter(ComboBox1.text)
    ElseIf (OptionButton2.Value = True) Then
        filter = txtFilter.text
    End If

    For i = 1 To params.Count

        ' GUI
        lblStatus.Caption = "Please, wait. The list of parameters with the specified filter applied is being built. " + _
                            Str(Round((i / params.Count) * 100#, 0)) + "%"

        Set param = params.Item(i)
        If InStr(param.Name, filter) > 0 Then

            If sel.Count > 0 Then
                ' Loop over selected items only
                
                For k = 1 To sel.Count
                    Set selEl = sel.Item(k)
                    If (InStr(1, param.Name, selEl.Reference.Name) > 0) Then
                    
                        If (chkExclude.Value = True And InStr(1, param.Name, "Activity")) Then
                            ' Activity parameter found - skip it if the corresponding checkbox is 'on'
                        Else
                            ListBox1.AddItem param.Name
                            ListBox2.AddItem " = " + Str(Val(param.ValueAsString))
                        End If
                        
                    End If
                Next k
                
            Else
                ' Nothing selected - loop over all parameters
                
                If InStr(param.Name, filter) > 0 Then
                
                    If (chkExclude.Value = True And InStr(1, param.Name, "Activity")) Then
                        ' Activity parameter found - skip it if the corresponding checkbox is 'on'
                    Else
                        ListBox1.AddItem param.Name
                        ListBox2.AddItem " = " + Str(Val(param.ValueAsString))
                    End If
                    
                End If
            End If
        End If
    Next i

    ' GUI
    lblStatus.Caption = "The list is built. Select the certain parameters, specify the addend and press 'Apply'."

    cmbApply.Enabled = True

End Sub

Private Sub cmbApply_Click()

    Dim prodDoc As ProductDocument
    Dim prod As Product
    Dim params As Parameters

    Set prodDoc = CATIA.ActiveDocument
    Set prod = prodDoc.Product
    Set params = prod.Parameters
    
    lblStatus.Caption = "Please, wait. The changes are being applied."

    Dim param As Parameter

    Dim i As Integer
    For i = 0 To ListBox1.ListCount - 1
        If ListBox1.Selected(i) = True Then

            Set param = params.GetItem(ListBox1.List(i))
            
            ' Only mm and deg are supported
            
            If InStr(1, param.ValueAsString, "mm") Then
                param.ValuateFromString Str(Val(param.ValueAsString) + Val(txtValue.text)) + "mm"
            ElseIf InStr(1, param.ValueAsString, "deg") Then
                param.ValuateFromString Str(Val(param.ValueAsString) + Val(txtValue.text)) + "deg"
            End If

        End If
    Next i

    lblStatus.Caption = "Changes are applied. Press 'Exit' to finish or specify the filter and press 'List' button."

End Sub

Private Sub cmbExit_Click()

    End

End Sub

Public Function textToFilter(txt As String) As String

    Dim filter As String

#If VBA7 Then

    Select Case txt
        Case "Translation, X axis":
            filter = "\X"
        Case "Translation, Y axis":
            filter = "\Y"
        Case "Translation, Z axis":
            filter = "\Z"
        Case "Rotation, X axis":
            filter = "Rotate.X"
        Case "Rotation, Y axis":
            filter = "Rotate.Y"
        Case "Rotation, Z axis":
            filter = "Rotate.Z"
    End Select
    
#Else

    Select Case txt
        Case "Translation, X axis":
            filter = "CoordX"
        Case "Translation, Y axis":
            filter = "CoordY"
        Case "Translation, Z axis":
            filter = "CoordZ"
        Case "Rotation, X axis":
            filter = "Rotate.X"
        Case "Rotation, Y axis":
            filter = "Rotate.Y"
        Case "Rotation, Z axis":
            filter = "Rotate.Z"
    End Select

#End If

    textToFilter = filter

End Function

Attribute VB_Name = "formMoverHelp"
Attribute VB_Base = "0{1AC7D426-4428-46C4-8CCC-71180DEF97BB}{C055D149-8551-45F9-9BA6-4433C3F572D8}"
Attribute VB_GlobalNameSpace = False
Attribute VB_Creatable = False
Attribute VB_PredeclaredId = True
Attribute VB_Exposed = False
Attribute VB_TemplateDerived = False
Attribute VB_Customizable = False
Private Sub UserForm_Initialize()

TextBox1.text = "CATIA v5 R21 (VBA6)" + vbNewLine + _
"Filters for translation:" + vbNewLine + _
"X Axis - CoordX" + vbNewLine + _
"Y Axis - CoordY" + vbNewLine + _
"Z Axis - CoordZ" + vbNewLine + _
"Filters for rotation:" + vbNewLine + _
"X Axis - Rotate.X" + vbNewLine + _
"Y Axis - Rotate.Y" + vbNewLine + _
"Z Axis - Rotate.Z" + vbNewLine + vbNewLine + _
"CATIA v5 R2015 (VBA7)" + vbNewLine + _
"Filters for translation:" + vbNewLine + _
"X Axis - \X" + vbNewLine + _
"Y Axis - \Y" + vbNewLine + _
"Z Axis - \Z" + vbNewLine + _
"Filters for rotation:" + vbNewLine + _
"X Axis - Rotate.X" + vbNewLine + _
"Y Axis - Rotate.Y" + vbNewLine + _
"Z Axis - Rotate.Z"

End Sub
