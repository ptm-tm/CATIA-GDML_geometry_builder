Attribute VB_Name = "MaterialsManager"
Sub CATMain()

    ' Language
    Dim builderLanguage As String
    builderLanguage = CATIA.SystemService.Environ("BuilderLanguage")
    If builderLanguage = "" Then builderLanguage = "English"

    ' GUI
    Select Case builderLanguage
    Case "English":
        formMaterialsManager.Caption = "Materials manager"
        formMaterialsManager.cmbCancel.Caption = "Exit"
        formMaterialsManager.Label1.Caption = "Current material:"
        formMaterialsManager.Label2.Caption = "New material:"
        formMaterialsManager.cmbAnalyse.Caption = "Analyse"
        formMaterialsManager.cmbApply.Caption = "Apply"
        formMaterialsManager.cmbModify.Caption = "Modify" + _
            vbNewLine + "Materials" + vbNewLine + "in documents"

    Case "Russian":
        formMaterialsManager.Caption = "Менеджер материалов"
        formMaterialsManager.cmbCancel.Caption = "Выход"
        formMaterialsManager.Label1.Caption = "Текущий материал:"
        formMaterialsManager.Label2.Caption = "Новый материал:"
        formMaterialsManager.cmbAnalyse.Caption = "Составить список"
        formMaterialsManager.cmbApply.Caption = "Применить"
        formMaterialsManager.cmbModify.Caption = "Применить" + _
            vbNewLine + "изменения" + vbNewLine + "в документах"

    End Select

    ' Show form
    formMaterialsManager.Show

End Sub

Attribute VB_Name = "formMaterialsManager"
Attribute VB_Base = "0{DC2299FC-0ECD-4EE8-A19C-D67D50DF14A0}{BAC55CA7-EFF9-4262-8CAC-1BD1A8C63C4E}"
Attribute VB_GlobalNameSpace = False
Attribute VB_Creatable = False
Attribute VB_PredeclaredId = True
Attribute VB_Exposed = False
Attribute VB_TemplateDerived = False
Attribute VB_Customizable = False
Option Explicit

Dim arrOld() As String
Dim arrNew() As String

Private Sub UserForm_Initialize()

    'Is active document a product?
    If (TypeName(CATIA.ActiveDocument) <> "ProductDocument") Then
        MsgBox "The type of the active document must be a product", vbCritical, "Incorrect active document type"
        End
    End If

    Dim prodDoc As ProductDocument
    Set prodDoc = CATIA.ActiveDocument
    
    ' Translate to design mode
'    MsgBox "Parts in this product are to be translated into 'Design Mode'" + vbNewLine + "This may take a few minutes, please wait.", vbExclamation, "Translate to Design mode"
'    prodDoc.Product.ApplyWorkMode DESIGN_MODE

End Sub

Private Sub cmbAnalyse_Click()

    Dim docs As Documents
    Dim prodDoc As ProductDocument
    Dim prodMain As Product
    Set docs = CATIA.Documents
    Set prodDoc = CATIA.ActiveDocument
    Set prodMain = prodDoc.Product

    ReDim arrOld(docs.Count)
    ReDim arrNew(docs.Count)

    Dim prtDoc As PartDocument
    Dim prt As Part
    Dim params As Parameters

    lstParts.Clear

' TODO - analyse the subproducts - not all the documents
' TODO - ignore not geant-like parts with warning

    Dim i As Integer
    For i = 1 To docs.Count
        If Right(docs.Item(i).Name, 8) = ".CATPart" Then
            Set prtDoc = docs.Item(i)
            Set prt = prtDoc.Part
            Set params = prt.Parameters

On Error GoTo MatNotFound
                arrOld(i - 2) = params.GetItem("Material").Value
                arrNew(i - 2) = params.GetItem("Material").Value
    
                lstParts.AddItem i - 2 & ":  " & prtDoc.Name & "  -  " & arrOld(i - 2) & "  -  " & arrNew(i - 2)
MatNotFound:
        End If

    Next i


End Sub

Private Sub lstParts_Click()

    txtCurMat.Text = arrOld(lstParts.ListIndex)
    txtNewMaterial.Text = arrNew(lstParts.ListIndex)

    txtNewMaterial.SetFocus

    txtNewMaterial.SelStart = 0
    txtNewMaterial.SelLength = Len(txtNewMaterial.Text)

End Sub

Private Sub cmbApply_Click()

    Dim tmp As String
    Dim firstDivPos As Integer
    Dim secDivPos As Integer
    Dim semicolonPos As Integer

    Dim nnn As String
    Dim prtName As String
    Dim oM As String
    Dim nM As String

    Dim i As Integer

    i = lstParts.ListIndex
    tmp = lstParts.List(i)

    arrNew(i) = txtNewMaterial.Text

    semicolonPos = InStr(1, tmp, ":  ", vbTextCompare)
    firstDivPos = InStr(semicolonPos + 3, tmp, "  -  ", vbTextCompare)
    secDivPos = InStr(firstDivPos + 5, tmp, "  -  ", vbTextCompare)

    nnn = Left(tmp, semicolonPos - 1)
    prtName = Mid(tmp, semicolonPos + 3, firstDivPos - semicolonPos - 3)
    oM = Mid(tmp, firstDivPos + 5, secDivPos - firstDivPos - 5)
    nM = Mid(tmp, secDivPos + 5)

    lstParts.RemoveItem i
    lstParts.AddItem nnn & ":  " & prtName & "  -  " & oM & "  -  " & arrNew(i), i

'    MsgBox Str(firstDivPos) & Chr(13) & _
'            Str(secDivPos) & Chr(13) & _
'            "/" & prtName & "/" & Chr(13) & _
'            "/" & oM & "/" & Chr(13) & _
'            "/" & nM & "/"

End Sub

Private Sub cmbModify_Click()

    Dim docs As Documents
    Dim prodDoc As ProductDocument
    Dim prodMain As Product
    Set docs = CATIA.Documents
    Set prodDoc = CATIA.ActiveDocument
    Set prodMain = prodDoc.Product

    Dim prod As Product
    Dim prtDoc As PartDocument
    Dim prt As Part
    Dim params As Parameters

    Dim i As Integer
    For i = 1 To docs.Count
        If Right(docs.Item(i).Name, 8) = ".CATPart" Then
            Set prtDoc = docs.Item(i)
            Set prt = prtDoc.Part
            Set params = prt.Parameters

            params.GetItem("Material").Value = arrNew(i - 2)
            prt.Update

        End If
    Next i

End Sub

Private Sub cmbCancel_Click()

    End

End Sub
