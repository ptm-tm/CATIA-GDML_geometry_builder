Attribute VB_Name = "CreateGeometryInCatia"
' Created by Oshkina Elena

Option Explicit

Dim AMOUNT_ELEMENTS_IN_GEOMETRICAL_SETS As Integer

Sub CreateGeometry(structTriangleData() As TriangleData, structVertex() As Vertex)

    AMOUNT_ELEMENTS_IN_GEOMETRICAL_SETS = 207
    'Dim RefP1 As Reference
    Dim x As Double, y As Double, z As Double
    Dim i As Integer
    Dim amountSets As Integer
    Dim vertex1Name As String, vertex2Name As String, vertex3Name As String
    CATIA.Documents.Add ("Part")
    amountSets = UBound(structTriangleData) / AMOUNT_ELEMENTS_IN_GEOMETRICAL_SETS

    'Declare 3D Tool box-------------------------
    Dim MyComponent As Part
    Set MyComponent = CATIA.ActiveDocument.Part
    Dim Wzk3D As Factory
    Set Wzk3D = MyComponent.HybridShapeFactory
    Dim indexGeometricalSet As Integer
    indexGeometricalSet = 1

    'Create Geometrical Set---------------
    Dim HBody As HybridBody, HBodyLines As HybridBody, HBodyFill As HybridBody, HBodyJoins As HybridBody
    Set HBody = MyComponent.HybridBodies.Add

    'HBody.HybridBodies.Add
    Set HBodyLines = MyComponent.HybridBodies.Add
    Set HBodyFill = MyComponent.HybridBodies.Add
    Set HBodyJoins = MyComponent.HybridBodies.Add

    HBodyJoins.name = "TesselatedSolidJoins"
    HBody.name = "TesselatedSolidPoints"
    HBodyLines.name = "TesselatedSolidLines"
    HBodyFill.name = "TesselatedSolidFill"

    Call CreateGeometricalSets(HBody, HBodyLines, HBodyFill, amountSets)

    Dim P1, P2, P3  As HybridShapePointCoord
    Dim myFill() As HybridShapeFill
    ReDim myFill(UBound(structTriangleData))
    Dim RefP1, RefP2, RefP3 As Reference
    
    'Declare object variable for hashTable
    Dim dictionaryForVertex As Dictionary
    
    'create object and connect with refference
    Set dictionaryForVertex = New Dictionary
    
    'Draw all points in the Geometric set
    Call DrawAllPointInGeometricalSet(structVertex, HBody, Wzk3D, MyComponent, dictionaryForVertex)
    
    
    'Draw all lines on existing points in the Geometrical Set
    
    For i = 0 To UBound(structTriangleData)
        'Each triangle has three vertices
        vertex1Name = structTriangleData(i).vertexName(0)
        vertex2Name = structTriangleData(i).vertexName(1)
        vertex3Name = structTriangleData(i).vertexName(2)

        'create links to points
'        Set RefP1 = FindPointInTree(vertex1Name, HBody, MyComponent)
'        Set RefP2 = FindPointInTree(vertex2Name, HBody, MyComponent)
'        Set RefP3 = FindPointInTree(vertex3Name, HBody, MyComponent)

        Set RefP1 = dictionaryForVertex(vertex1Name)
        Set RefP2 = dictionaryForVertex(vertex2Name)
        Set RefP3 = dictionaryForVertex(vertex3Name)
        
        'Predefine Line------------------------
        Dim Line1, Line2, Line3 As HybridShapeLinePtPt
        Set Line1 = Wzk3D.AddNewLinePtPt(RefP1, RefP2)
        Set Line2 = Wzk3D.AddNewLinePtPt(RefP2, RefP3)
        Set Line3 = Wzk3D.AddNewLinePtPt(RefP1, RefP3)

        'Create Lines in GS
        HBodyLines.HybridBodies.Item(indexGeometricalSet).AppendHybridShape Line1
        HBodyLines.HybridBodies.Item(indexGeometricalSet).AppendHybridShape Line2
        HBodyLines.HybridBodies.Item(indexGeometricalSet).AppendHybridShape Line3
        If i Mod AMOUNT_ELEMENTS_IN_GEOMETRICAL_SETS = 0 And i <> 0 Then
            indexGeometricalSet = indexGeometricalSet + 1
        End If

    Next i 'Go to the next triangle

    MyComponent.Update

    Call CreateTrianglesFromLines(myFill(), HBodyFill, Wzk3D, HBodyLines, MyComponent)

    Dim join As HybridShapeAssemble
    Set join = CombinateGeometryIntoOneElement(MyComponent, myFill(), UBound(structTriangleData), Wzk3D) 'for join
    HBodyJoins.AppendHybridShape join
    MyComponent.Update

    'Hide geometrical set
    Dim mBody As Body
    Set mBody = MyComponent.MainBody
    MyComponent.InWorkObject = mBody

    Dim shapeFactory1 As ShapeFactory
    Dim reference2 As Reference
    Dim closeSurface1 As CloseSurface
    Set shapeFactory1 = MyComponent.ShapeFactory
    Set reference2 = MyComponent.CreateReferenceFromObject(join)
    Set closeSurface1 = shapeFactory1.AddNewCloseSurface(reference2)
    
    ' ----------------------------------------------------------------
    MyComponent.Update

    ' ----------------------------------------------------------------
    Dim MyList As Selection
    Set MyList = CATIA.ActiveDocument.Selection
    MyList.Clear
    MyList.Add MyComponent.HybridBodies.Item("TesselatedSolidPoints")
    MyList.Add MyComponent.HybridBodies.Item("TesselatedSolidLines")
    MyList.Add MyComponent.HybridBodies.Item("TesselatedSolidFill")
    MyList.Add MyComponent.HybridBodies.Item("TesselatedSolidJoins")

    MyList.VisProperties.SetShow catVisPropertyNoShowAttr

End Sub

Sub CreateGeometricalSets(ByRef HBody As HybridBody, _
                            ByRef HBodyLines As HybridBody, _
                            ByRef HBodyFill As HybridBody, _
                            amountSets As Integer)

    Dim i As Integer
    Dim HBodyTemp As HybridBody
    
    For i = 1 To CInt(amountSets / 2)
        Set HBodyTemp = HBody.HybridBodies.Add
        HBodyTemp.name = "TesselatedSolidPoints" & i
    Next i
    
    For i = 1 To amountSets + 1
        Set HBodyTemp = HBodyFill.HybridBodies.Add
        HBodyTemp.name = "TesselatedSolidFill" & i
        Set HBodyTemp = HBodyLines.HybridBodies.Add
        HBodyTemp.name = "TesselatedSolidLines" & i
    Next i
    
End Sub

'Function FindPointInTree(vertex1Name As String, HBody As HybridBody, MyComponent As Part) As Reference
'
'    Dim RefP1 As Reference
'    Dim RefP2 As Reference
'    Dim RefP3 As Reference
'    Dim P1 As HybridShapePointCoord
'
'    Dim i As Integer
'    Dim j As Integer
'    Dim k As Integer
'    k = 0
'
'    Dim index As Integer
'    index = Right(vertex1Name, InStr(vertex1Name, "v"))
'
'    ' !!!!!!!!!!!!!!!!!!!!!!!!!!!!!!!!!!!!!! OPTIMIZE !!!!!!!!!!!!!!!!!!!!!!!!!!!!!!!!!!!!!!
'    For i = 1 To HBody.HybridBodies.Count
'        For j = 1 To HBody.HybridBodies.Item(i).HybridShapes.Count
'            If HBody.HybridBodies.Item(i).HybridShapes.Item(j).name = vertex1Name Then
'                Set P1 = HBody.HybridBodies.Item(i).HybridShapes.Item(j)
'                k = 1
'                Exit For
'            End If
'        Next j
'        If k = 1 Then
'            Exit For
'        End If
'    Next i
'
'    Set RefP1 = MyComponent.CreateReferenceFromObject(P1)
'    Set FindPointInTree = RefP1
'
'End Function

Sub CreateTrianglesFromLines(ByRef myFill() As HybridShapeFill, _
                             ByRef HBodyFill As HybridBody, _
                             ByRef Wzk3D As Factory, _
                             HBodyLines As HybridBody, _
                             ByRef MyComponent As Part)

        Dim Line1, Line2, Line3 As HybridShapeLinePtPt
        Dim RefL1, RefL2, RefL3 As Reference
        Dim i As Integer, j As Integer, k As Integer
        j = 0
        Dim indexGeometricalSet As Integer
        indexGeometricalSet = 1
        
        For k = 1 To HBodyLines.HybridBodies.Count
            For i = 1 To HBodyLines.HybridBodies.Item(k).HybridShapes.Count - 2 Step 3
            
                Set Line1 = HBodyLines.HybridBodies.Item(k).HybridShapes.Item(i)
                Set Line2 = HBodyLines.HybridBodies.Item(k).HybridShapes.Item(i + 1)
                Set Line3 = HBodyLines.HybridBodies.Item(k).HybridShapes.Item(i + 2)
    
                Set RefL1 = MyComponent.CreateReferenceFromObject(Line1)
                Set RefL2 = MyComponent.CreateReferenceFromObject(Line2)
                Set RefL3 = MyComponent.CreateReferenceFromObject(Line3)
    
                Set myFill(j) = Wzk3D.AddNewFill
                myFill(j).AddBound RefL1
                myFill(j).AddBound RefL2
                myFill(j).AddBound RefL3
                HBodyFill.HybridBodies.Item(k).AppendHybridShape myFill(j)
                j = j + 1
            Next i
        Next k
        MyComponent.Update
        'Assign Fill to the Geometrical Set------------
        
End Sub

'Drawing all vertices from the set, each vertex is named in the Geometrical set: "v0", "v1" ....
Sub DrawAllPointInGeometricalSet(structVertex() As Vertex, _
                                 ByRef HBody As HybridBody, _
                                 ByRef Wzk3D As Factory, _
                                 ByRef MyComponent As Part, ByRef dictionaryForVertex As Dictionary)

    Dim P1 As HybridShapePointCoord
    Dim x As Double, y As Double, z As Double
    Dim RefP1 As Reference
    Dim indexGeometricalSet As Integer
    indexGeometricalSet = 1
    
    Dim i As Integer
    For i = 0 To UBound(structVertex)
        'Get coordinates for vertex
        x = structVertex(i).x
        y = structVertex(i).y
        z = structVertex(i).z
        'Create point  by coordinates
        Set P1 = Wzk3D.AddNewPointCoord(x, y, z)
        P1.name = structVertex(i).name
        'Creating reference for points
        Set RefP1 = MyComponent.CreateReferenceFromObject(P1)
        'Assign Points to Geometrical Set------------------
        HBody.HybridBodies.Item(indexGeometricalSet).AppendHybridShape P1
        'Save Point in hashTable ("vertex0", reference)
        dictionaryForVertex.Add P1.name, RefP1
        If i Mod AMOUNT_ELEMENTS_IN_GEOMETRICAL_SETS = 0 And i <> 0 Then
            indexGeometricalSet = indexGeometricalSet + 1
        End If
    Next i

    MyComponent.Update

End Sub

Sub GetCoordinatesForEachVertex(vertex1Name As String, ByRef x, ByRef y, ByRef z, structVertex() As Vertex)

    Dim index As Integer
    'The vertex name contains an index by which it can be found in an array: no need to go over all
    Dim strIndexOfVertes As String
    strIndexOfVertes = Mid(vertex1Name, 2) ' v1,  v2, v202
    index = CInt(strIndexOfVertes)
    x = structVertex(index).x
    y = structVertex(index).y
    z = structVertex(index).z

End Sub

Function CombinateGeometryIntoOneElement(ByRef MyComponent As Part, _
                                         ByRef myFill() As HybridShapeFill, _
                                         amountTriangels As Integer, _
                                         ByRef Wzk3D As Factory) As HybridShapeAssemble

    Dim myJoin As HybridShapeAssemble
    Dim i As Integer
    Dim Ref() As Reference
    ReDim Ref(amountTriangels)
    For i = 0 To amountTriangels
        Set Ref(i) = MyComponent.CreateReferenceFromObject(myFill(i))
    Next i
    Set myJoin = Wzk3D.AddNewJoin(Ref(0), Ref(1))
    For i = 0 To amountTriangels - 2
        myJoin.AddElement Ref(i + 2)
    Next i
    'Assign join to Geometrical Set
    Set CombinateGeometryIntoOneElement = myJoin
 
End Function

Attribute VB_Name = "DefinitionOfStructures"
' Created by Oshkina Elena

Option Explicit

Type Vertex
    x As Double
    y As Double
    z As Double
    name As String
End Type

Public structVertex() As Vertex

Type TriangleData
    vertexName(2) As String
End Type

Public structTriangleData() As TriangleData

Type quadrangularData
    vertexName(3) As String
End Type

Public structQuadrangularData() As quadrangularData

Attribute VB_Name = "MainModule"
' Created by Oshkina Elena

Option Explicit

Public Sub CATMain()

    formGDML2STL.Show vbModal
    
End Sub

Attribute VB_Name = "formGDML2STL"
Attribute VB_Base = "0{26522C40-F4A7-4D25-AFE5-3CE060D7473C}{C3AC7AE5-FA95-49DF-80AB-A7B8F1789119}"
Attribute VB_GlobalNameSpace = False
Attribute VB_Creatable = False
Attribute VB_PredeclaredId = True
Attribute VB_Exposed = False
Attribute VB_TemplateDerived = False
Attribute VB_Customizable = False
Option Explicit

Private Sub cmbStart_Click()

    CATIA.RefreshDisplay = False
    
    Dim nameOfFile As String
    Dim nameTesselSolid As String
    nameTesselSolid = "tessel"
    
    Dim GDML As MSXML2.DOMDocument
    Set GDML = New DOMDocument
    
    nameOfFile = formGDML2STL.txtGDML.Text
    Dim loadSuccess As Boolean
    loadSuccess = GDML.Load(nameOfFile)
    If (Not loadSuccess) Then
        MsgBox "Failed to load file " + nameOfFile + ". Aborting.", vbCritical
        Exit Sub
    End If
    
    'Arrays for storing the coordinates of vertices
    Dim arrCoordinatesX() As Double
    Dim arrCoordinatesY() As Double
    Dim arrCoordinatesZ() As Double
    
    'Memory allocation for the vertex array
    ReDim arrCoordinatesX(0)
    ReDim arrCoordinatesY(0)
    ReDim arrCoordinatesZ(0)
    Dim i As Integer
    
    'Array for storing vertex names
    Dim arrNameOfVertex() As String
    ReDim arrNameOfVertex(0)
    
    lblStatus.Caption = "Step 1" 'TODO fix - it doesn't work
    
    'Filling the data structure with xml
    Call getDataFromGDML.GetCoordinatesValueFromGDML(GDML, nameTesselSolid, arrNameOfVertex)
    
    lblStatus.Caption = "Step 2" 'TODO fix - it doesn't work
    
    'Fill arrays with coordinatesFill arrays with coordinates
    Call getDataFromGDML.GetArraysOfCoordinatesGDML(arrCoordinatesX(), arrCoordinatesY(), arrCoordinatesZ(), GDML, arrNameOfVertex)
 
    lblStatus.Caption = "Step 3" 'TODO fix - it doesn't work
 
    'Creation of geometry in CATIA
    Call CreateGeometryInCatia.CreateGeometry(structTriangleData, structVertex)
    
    lblStatus.Caption = "Done." 'TODO fix - it doesn't work
    
    MsgBox "Conversion successfully completed.", vbOKOnly

End Sub

Private Sub cmbExit_Click()

    End

End Sub

Private Sub UserForm_Initialize()

    formGDML2STL.txtGDML.Text = "C:\Egor\CATIA-GDML_geometry_builder\elena.txt"

End Sub

Attribute VB_Name = "getDataFromGDML"
' Created by Oshkina Elena

Option Explicit

Sub GetCoordinatesValueFromGDML(ByRef GDML As MSXML2.DOMDocument, nameTesselSolid As String, ByRef arrNameOfVertex() As String)

    Dim solidNodes As IXMLDOMNodeList
    Dim solidNode As IXMLDOMNode
    Dim solidList As IXMLDOMNodeList
    Set solidNodes = GDML.getElementsByTagName("solids")
    
    Set solidNode = solidNodes.Item(0)
    Set solidList = solidNode.childNodes ' box box tesselated
    Dim j As Integer
    
    For j = 0 To solidList.Length - 1
        If solidList.Item(j).Attributes.getNamedItem("name").nodeValue = nameTesselSolid Then
            Exit For
        End If
    Next

    ReDim structTriangleData(0) ' allocate memory for an array of structures of triangles that store information about the vertices of their constituents
    
    Dim v1, v2, v3 As String
    Dim i, n, k As Integer
    k = 0
    'We get the names of the vertices of which each triangle consists
    For i = 0 To solidList.Item(j).childNodes.Length - 1
    If solidList.Item(j).childNodes.Item(i).baseName Like "triangular" Then
    
        v1 = solidList.Item(j).childNodes.Item(i).Attributes.getNamedItem("vertex1").nodeValue
        v2 = solidList.Item(j).childNodes.Item(i).Attributes.getNamedItem("vertex2").nodeValue
        v3 = solidList.Item(j).childNodes.Item(i).Attributes.getNamedItem("vertex3").nodeValue
        'We store the names of vertices in an array of structures
        structTriangleData(i).vertexName(0) = v1
        structTriangleData(i).vertexName(1) = v2
        structTriangleData(i).vertexName(2) = v3
        If VertexInStringArray(arrNameOfVertex, CStr(v1)) = False Then ' If there is no vertex with this name in the array of vertex names
            arrNameOfVertex(k) = v1
            ReDim Preserve arrNameOfVertex(UBound(arrNameOfVertex) + 1)
            k = k + 1
        End If
        If VertexInStringArray(arrNameOfVertex, CStr(v2)) = False Then ' If there is no vertex with this name in the array of vertex names
            arrNameOfVertex(k) = v2
            ReDim Preserve arrNameOfVertex(UBound(arrNameOfVertex) + 1)
            k = k + 1
        End If
        If VertexInStringArray(arrNameOfVertex, CStr(v3)) = False Then ' If there is no vertex with this name in the array of vertex names
            arrNameOfVertex(k) = v3
            ReDim Preserve arrNameOfVertex(UBound(arrNameOfVertex) + 1)
            k = k + 1
        End If
         ReDim Preserve structTriangleData(UBound(structTriangleData) + 1)
    End If
    Next i

    ReDim Preserve arrNameOfVertex(UBound(arrNameOfVertex) - 1) ' Correct the number of unique vertices
    ReDim Preserve structTriangleData(UBound(structTriangleData) - 1)

End Sub

Sub GetArraysOfCoordinatesGDML(ByRef arrCoordinatesX() As Double, ByRef arrCoordinatesY() As Double, ByRef arrCoordinatesZ() As Double, ByRef GDML As MSXML2.DOMDocument, arrNameOfVertex() As String)

    Dim defineNode As IXMLDOMNode
    Dim defineNodesList As IXMLDOMNodeList
    Set defineNode = GDML.getElementsByTagName("define").Item(0)
    Set defineNodesList = defineNode.childNodes
    Dim i, index, amount As Integer
    Dim vertexName As String
    Dim existVertex As Integer
    ReDim structVertex(0) 'allocate memory for an array of structures for coordinates
    index = 0
    For i = 0 To defineNodesList.Length - 1
    If Not (defineNodesList.Item(i).nodeName = "#comment") Then
    'If the vertex name is in the list of vertices of the current tesselated solid
    
        If defineNodesList.Item(i).nodeName = "position" Then
             vertexName = defineNodesList.Item(i).Attributes.Item(0).nodeValue
             existVertex = inList(vertexName, arrNameOfVertex)
             If existVertex = 1 Then
                    amount = UBound(arrCoordinatesX) 'the current number of elements in the array
                    ' x
                    arrCoordinatesX(index) = CDbl(Val(defineNodesList.Item(i).Attributes.Item(2).nodeValue))
                    'y
                    arrCoordinatesY(index) = CDbl(Val(defineNodesList.Item(i).Attributes.Item(3).nodeValue))
                    'z
                    arrCoordinatesZ(index) = CDbl(Val(defineNodesList.Item(i).Attributes.Item(4).nodeValue))
        
                    structVertex(index).name = vertexName
                    structVertex(index).x = arrCoordinatesX(index)
                    structVertex(index).y = arrCoordinatesY(index)
                    structVertex(index).z = arrCoordinatesZ(index)
        
                    ' At each step, we increase the size of the array by 1 for the next coordinate
                    ReDim Preserve arrCoordinatesX(amount + 1)
                    ReDim Preserve arrCoordinatesY(amount + 1)
                    ReDim Preserve arrCoordinatesZ(amount + 1)
                    ReDim Preserve structVertex(UBound(structVertex) + 1)
                    index = index + 1
             End If
        End If
    End If
    Next i
    
    ReDim Preserve arrCoordinatesX(UBound(arrCoordinatesX) - 1) ' We correct the number of coordinates x
    ReDim Preserve arrCoordinatesY(UBound(arrCoordinatesY) - 1) ' We correct the number of coordinates y
    ReDim Preserve arrCoordinatesZ(UBound(arrCoordinatesZ) - 1) ' We correct the number of coordinates z
    ReDim Preserve structVertex(UBound(structVertex) - 1)

End Sub

'If the vertex exists in the current tessel, then return 1
Function inList(vertexName As String, arrNameOfVertex() As String) As Integer

    Dim y As Integer
    Dim i As Integer
    y = 0
    For i = 0 To UBound(arrNameOfVertex())
        If vertexName Like arrNameOfVertex(i) Then
            y = 1
            Exit For
        End If
    Next i
    
    inList = y
    
End Function

Function VertexInStringArray(arrNameOfVertex() As String, nameVertex As String) As Boolean 'If the vertex with this name is not yet in the array, return false

    Dim i As Integer
    Dim k As Integer
    
    k = 0
    For i = 0 To UBound(arrNameOfVertex)
        If arrNameOfVertex(i) = nameVertex Then
            k = k + 1
            Exit For
        End If
    Next i
    
    If k > 0 Then
        VertexInStringArray = True
    Else
        VertexInStringArray = False
    End If
    
End Function
